FME workspace BuildingsRefinement.fmw
Title: BuildingsRefinement
Description: General note:
    This is a implementation of the methodology presented in the thesis:
    "Semantic-based Geometry Refinement of 3D City Models for Testing Automated Driving"
    Study case:
    Buildings
History: 09.08.2020,OlafWysocki,

Parameters:
- SourceDataset_LAS = ""D:\projects\MasterThesis\Ingolstadt\raw\mls\38070110001_38070110002_Scannerpunkte.las" "D:\projects\MasterThesis\Ingolstadt\raw\mls\38070110002_38070110003_Scannerpunkte.las" "D:\projects\MasterThesis\Ingolstadt\raw\mls\38070110003_38070110004_Scannerpunkte.las" "D:\projects\MasterThesis\Ingolstadt\raw\mls\38070110004_38070110005_Scannerpunkte.las" "D:\projects\MasterThesis\Ingolstadt\raw\mls\38070110005_38070110006_Scannerpunkte.las" "D:\projects\MasterThesis\Ingolstadt\raw\mls\38071110001_38071110002_Scannerpunkte.las" "D:\projects\MasterThesis\Ingolstadt\raw\mls\38072110001_38072110002_Scannerpunkte.las" "D:\projects\MasterThesis\Ingolstadt\raw\mls\38073110001_38073110002_Scannerpunkte.las" "D:\projects\MasterThesis\Ingolstadt\raw\mls\38074110001_38074110002_Scannerpunkte.las" "D:\projects\MasterThesis\Ingolstadt\raw\mls\38074110002_38074110003_Scannerpunkte.las" "D:\projects\MasterThesis\Ingolstadt\raw\mls\38074110003_38074110004_Scannerpunkte.las" "D:\projects\MasterThesis\Ingolstadt\raw\mls\38075110001_38075110002_Scannerpunkte.las" "D:\projects\MasterThesis\Ingolstadt\raw\mls\38076110001_38076110002_Scannerpunkte.las" "D:\projects\MasterThesis\Ingolstadt\raw\mls\38077110001_38077110002_Scannerpunkte.las" "D:\projects\MasterThesis\Ingolstadt\raw\mls\38078110001_38078110002_Scannerpunkte.las" "D:\projects\MasterThesis\Ingolstadt\raw\mls\38079110001_38079110002_Scannerpunkte.las" "D:\projects\MasterThesis\Ingolstadt\raw\mls\38080110001_38080110002_Scannerpunkte.las" "D:\projects\MasterThesis\Ingolstadt\raw\mls\38081110001_38081110002_Scannerpunkte.las""   # Source ASPRS LAS File(s)
- FEATURE_TYPES =   # LAS Feature Types to Read
- RANGE_SLIDER = 8   # userOctreeDepth RANGE:[,] Please, provide octree depth
- RANGE_SLIDER = 0
- RANGE_SLIDER = 0.01
- autoClean = true   # Set up some cleaning to the process, like erasing unreferenced vertices, bad faces, etc.
- FILENAME_MUSTEXIST = C:\MasterThesis\Workbenches\MeshLabServer\Test.mlx   # XMLinput Config_mlx|*.mlx Select the configuration template file
- FILENAME = C:\MasterThesis\Workbenches\MeshLabServer\Config.mlx   # XMLOutput Config_mlx|*.mlx Select location to save the meshlab configuration file
- FILENAME_MUSTEXIST = C:\Software\VCG\MeshLab\meshlabserver.exe   # meshlabserver meshlabserver_exe|*.exe Select meshlabserver.exe file path
- LASTOOL = D:\projects\PassageFinder\workbench\lookUpWorkbench\LAStools\bin\lasheight.exe   # Lasheight.exe location
- HEIGHTSTORAGE = -store_in_user_data
- HEIGHTSTORAGESCALE = 10   # Height storage scaling (for "Store in user data" only)
- tmpXYZ = C:\MasterThesis\Processing\IntermediatePointCloud_1\Road_1_xyz   # Select tmp folder for Building point cloud SHOULD DIFFER from other BUILDING path
- tmpXYZbld = C:\MasterThesis\Processing\IntermediatePointCloud_1\Building_1_xyz   # Select tmp folder for Building point cloud SHOULD DIFFER from other Building path
- SourceDataset_CITYGML = D:\projects\MasterThesis\Ingolstadt\raw\citygml\lod1\AreaOfInterestsOfLod3\Innestadt_areaOfLod3.gml   # Source CityGML File(s)
- tmpXYZbldInliers = C:\MasterThesis\Processing\IntermediatePointCloud_1\Building_1_xyz\XYZinliers   # Select a path for found inliers within buildings
- DestDataset_CITYGML = D:\bld\bld8lvl.gml   # Destination CityGML Document

Readers:
- LAS_1: LAS from $(SourceDataset_LAS)
- CITYGML_1: CITYGML from $(SourceDataset_CITYGML)

Writers:
- CITYGML_3: CITYGML to $(DestDataset_CITYGML)

Note: General note: / This is a implementation of the methodology presented in the thesis: / "Semantic-based Geometry Refinement of 3D City Models for Testing Automated Driving"
Note: Study case: / Buildings
Note: Before running check Published Parameters to fine-tune expected results!
Note: Good practices:
Note: Clean tmp folders after each processing to assure stability and efficiency
Note: Big objects (>500 m2) process separately

Bookmark: 1.2: PointCloud MLS
LAS (reader LAS_1)
    -> CoordinateSystemSetter_3
CoordinateSystemSetter_3
    COORDSYS = EPSG:32632
    -> AttributeCreator
AttributeCreator
    ATTR_TABLE = SET_TO PointCloud = MLS
    -> Junction
Note: PointCloud vs CityGML
Junction
    -> Junction_2

Bookmark: 2.1.3.1: PointCloud vs CityGML
Note: LAS MLS
Junction_2
    -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttCleaner
AttCleaner: AttributeRemover
    LIST_ATTRS = citygml_address{} citygml_address{}.xlink_href citygml_appearance_member{} citygml_appearance_member{}.xlink_href citygml_appearance{} citygml_appearance{}.xlink_href citygml_auxiliary_traffic_area{} citygml_auxiliary_traffic_area{}.xlink_href citygml_bounded_by{} citygml_bounded_by{}.xlink_href citygml_city_object_member{} citygml_city_object_member{}.xlink_href citygml_consists_of_building_part{} citygml_consists_of_building_part{}.xlink_href citygml_function{} citygml_function{}.codeSpace citygml_generalizes_to{} citygml_generalizes_to{}.xlink_href citygml_interior_building_installation{} citygml_interior_building_installation{}.xlink_href citygml_interior_room{} citygml_interior_room{}.xlink_href citygml_level_of_detail{} citygml_opening{} citygml_opening{}.xlink_href citygml_outer_building_installation{} citygml_outer_building_installation{}.xlink_href citygml_traffic_area{} citygml_traffic_area{}.xlink_href citygml_usage{} citygml_usage{}.codeSpace externalReference{} externalReference{}.externalObject.name externalReference{}.externalObject.uri externalReference{}.informationSystem gml_feature_member{} gml_feature_member{}.xlink_href
    REMOVE_ATTRS = Accuracy,_clipped,citygml_address{0}.xlink_href,citygml_appearance_member{0}.xlink_href,citygml_appearance{0}.xlink_href,citygml_auxiliary_traffic_area{0}.xlink_href,citygml_bounded_by{0}.xlink_href,citygml_city_object_member{0}.xlink_href,citygml_class,citygml_class_codeSpace,citygml_consists_of_building_part{0}.xlink_href,citygml_creationDate,citygml_crown_diameter,citygml_crown_diameter_units,citygml_feature_role,citygml_feature_role_attr_name,citygml_feature_role_attr_val,citygml_function{0},citygml_function{0}.codeSpace,citygml_generalizes_to{0}.xlink_href,citygml_height,citygml_height_units,citygml_interior_building_installation{0}.xlink_href,citygml_interior_room{0}.xlink_href,citygml_level_of_detail{0},citygml_measured_height,citygml_measured_height_units,citygml_outer_building_installation{0}.xlink_href,citygml_relative_to_terrain,citygml_relative_to_water,citygml_roof_type,citygml_roof_type_codeSpace,citygml_species,citygml_species_codeSpace,citygml_storey_heights_above_ground,citygml_storey_heights_above_ground_units,citygml_storey_heights_below_ground,citygml_storey_heights_below_ground_units,citygml_storeys_above_ground,citygml_storeys_below_ground,citygml_target_uri,citygml_terminationDate,citygml_traffic_area{0}.xlink_href,citygml_trunk_diameter,citygml_trunk_diameter_units,citygml_usage{0},citygml_usage{0}.codeSpace,citygml_year_of_construction,citygml_year_of_demolition,externalReference{0}.externalObject.name,externalReference{0}.externalObject.uri,externalReference{0}.informationSystem,fme_basename,gml_description,gml_feature_member{0}.xlink_href,opendrive_laneSection_index,opendrive_laneSection_start,opendrive_lane_id,opendrive_lane_level,opendrive_lane_material_friction,opendrive_lane_material_roughness,opendrive_lane_material_surface,opendrive_lane_roadMark_color,opendrive_lane_roadMark_material,opendrive_lane_roadMark_type,opendrive_lane_roadMark_weight,opendrive_lane_speed_max,opendrive_lane_type,opendrive_roadObject_dynamic,opendrive_roadObject_id,opendrive_roadObject_name,opendrive_roadObject_orientation,opendrive_roadObject_type,opendrive_roadObject_validLength,opendrive_roadSignal_countryCode,opendrive_roadSignal_dynamic,opendrive_roadSignal_id,opendrive_roadSignal_name,opendrive_roadSignal_orientation,opendrive_roadSignal_subtype,opendrive_roadSignal_type,opendrive_roadSignal_value,opendrive_road_id,opendrive_road_junction,opendrive_road_length,opendrive_road_rule,Dachneigung,Dachorientierung,DataAvalaible,DatenquelleBodenhoehe,DatenquelleDachhoehe,DatenquelleLage,Flaeche,Gemeindeschluessel,HoeheDach,HoeheGrund,LoD,Methode,NiedrigsteTraufeDesGebaeudes,PosMH,RelHeight,StandLK,Z_MAX,Z_MAX_ASL,Z_MIN,Z_MIN_ASL,_overlaps,citygml_address,citygml_function,citygml_opening{0}.xlink_href,fme_feature_type,minHeight,opendrive_lane_speed_max_units,topHeight
    -> MLScombiner_2
MLScombiner_2: PointCloudCombiner
    ACCUM_ATTRS_NAME = Yes
    EXTRACT_RASTER_NODATA_NAME = No
    GROUP_BY = gml_id
    SPACING = 1.0
    -> LAStools.lasground_2 [PointCloud]

Bookmark: 1.1: HDMapAsCityGML_noOffset -> LOD1
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
Road (reader CITYGML_1)
    attributes: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
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, opendrive_roadObject_dynamic xml_buffer, opendrive_roadObject_id xml_buffer, opendrive_roadObject_name xml_buffer, opendrive_roadObject_orientation xml_buffer, opendrive_roadObject_type xml_buffer, opendrive_road_id xml_buffer, opendrive_road_junction xml_buffer, opendrive_road_length xml_buffer, opendrive_road_rule xml_buffer
    -> CoordinateSystemSetter_8
CoordinateSystemSetter_8
    COORDSYS = EPSG:32632
    -> Junction_5
Note: go to SYSTEM
Junction_5
    -> Junction_6

Bookmark: 2.1.1: Preprocessing
Note: LOD1
Junction_6
    -> setLoDAttribute
    -> TestFilter [off]
    -> Separate_processing [off]
Note: Pass to Local CRS shift / -> Surface Reconstruction
Junction_3
    -> Junction_4
Note: Pass to writer
Junction_25
    -> Junction_26

Bookmark: 2.1.1.1: Possible testing sides...
TestFilter
    DEFAULT_VALUE = <UNFILTERED>
    TEST_LIST = "BOOL_OP,OR,COMPOSITE_TEST,""""""1"""""",TEST_CLAUSE,TEST @Value(gml_id) = UUID_88f4a67f-ab81-4338-9e61-f916e9a60298",redbld,"BOOL_OP,OR,COMPOSITE_TEST,""""""1"""""",TEST_CLAUSE,TEST @Value(gml_id) = UUID_164404b3-516e-4cea-b609-c9c74f8f638a",byTheGate,"BOOL_OP,OR,COMPOSITE_TEST,""""""1"""""",TEST_CLAUSE,TEST @Value(gml_id) = UUID_e71e52b2-fa61-4558-ab18-500572d8b52d",narrowStreet1a,"BOOL_OP,OR,COMPOSITE_TEST,""""""1"""""",TEST_CLAUSE,TEST @Value(gml_id) = UUID_93cdd3f9-6170-431c-8667-e3663fa51dc4",narrowStreet1,"BOOL_OP,OR,COMPOSITE_TEST,""""""1"""""",TEST_CLAUSE,TEST @Value(gml_id) = UUID_2f7ad23d-4b29-4921-8d0c-1dcff0c61188",in a row
    redbld -> setLoDAttribute [off]
    byTheGate -> setLoDAttribute [off]
    narrowStreet1a -> setLoDAttribute [off]
    narrowStreet1 -> setLoDAttribute [off]
    in a row -> setLoDAttribute [off]
Note: enable if separate processing (see CityGMLMerger.fmw) needed
Separate_processing: TestFilter
    DEFAULT_VALUE = <UNFILTERED>
    TEST_LIST = "BOOL_OP,OR,COMPOSITE_TEST,""""""1"""""",TEST_CLAUSE,TEST @Value(gml_id) = UUID_0b38ec1a-7a19-4b0d-894b-4a3819a366d5",big1,"BOOL_OP,OR,COMPOSITE_TEST,""""""1"""""",TEST_CLAUSE,TEST @Value(gml_id) = UUID_e67a8858-c4fb-49e8-a06b-3bdb52108475",seltsam10lvl
    big1 -> setLoDAttribute [off]
    seltsam10lvl -> setLoDAttribute [off]

Bookmark: 2.1.1.2: Extract and set attributes, assumptions
Note: create attribute instead of list for LoD
setLoDAttribute: AttributeCreator
    ATTR_TABLE = SET_TO LoD = @Value(citygml_level_of_detail{0})
    -> TopMinObjectsHeight
TopMinObjectsHeight: BoundsExtractor
    ZMAX = topHeight
    ZMIN = minHeight
    -> AddLODDepAccAttributes
Note: create attribute for later buffer (X,Y)/offset (Z) depending on LoD -> CityGML Enconding standards
AddLODDepAccAttributes: AttributeCreator
    ATTR_TABLE = SET_TO Accuracy = FME_CONDITIONAL:DEFAULT_VALUE'_FME_NO_OP_'BOOL_OP;OR;COMPOSITE_TEST;1;TEST @Value(LoD) = 1'5'BOOL_OP;OR;COMPOSITE_TEST;1;TEST @Value(LoD) = 2'2'BOOL_OP;OR;COMPOSITE_TEST;1;TEST @Value(LoD) = 3'0.5'BOOL_OP;OR;COMPOSITE_TEST;1;TEST @Value(LoD) = 4'0.2'FME_NUM_CONDITIONS5___
    -> PossibleHeightDevi
PossibleHeightDevi: AttributeCreator
    ATTR_TABLE:
      SET_TO PosMH = @Evaluate(@sub(@Value(minHeight),@Value(Accuracy)))
      SET_TO RelPosHeight = @sub(@Value(topHeight),@Value(PosMH))
      SET_TO RHeight = @sub(@Value(topHeight),@Value(minHeight))
    -> SurfaceNormalExtractor
    -> Junction_25
    -> AttributeKeeper

Bookmark: 2.1.2.1: Needed for LoD1 to find GroundSurface
SurfaceNormalExtractor
    -> GeometryPartExtractor
Note: select ground /flat surface based on normals
GeometryPartExtractor
    GQUERY:
      for $geom in //geometry
      where fme:get-trait($geom, 'surface_normal_z')/number() < 0
      return number($geom/@fme_id)
    EXTRACTED -> Aggregator
    REMAINING -> Junction_7
Aggregator
    ACCUM_ATTRS_NAME = Use Attributes From One Feature
    AGGREGATE_TYPE = Homogeneous Collection (If Possible)
    GROUP_BY = gml_id
    MODE = Geometry - Assemble One Level
    SEP = ,
    AGGREGATE -> 2DForcer
2DForcer
    2D -> Respective_Accuracy2D_buffer

Bookmark: 2.1.2: Buffer creation
Note: pass wall structures only
Junction_7
    -> Junction_8

Bookmark: 2.3.1: Evaluation of point cloud density per wall
Note: only raw walls of buildings
Note: Calculate density of point cloud and check whether it covers walls
Junction_8
    -> GeometryPartExtractor_3
Note: MLS PointCloud NON ground
Junction_18
    -> Clipper_3 [CLIPPEE]
    -> Tiler

Bookmark: 2.3.1.1: Retrieve only walls
Note: select walls based on normals
GeometryPartExtractor_3
    GQUERY:
      for $geom in //geometry
      where fme:trait-equals(fme:get-trait($geom, 'surface_normal_z'), '0')
      return number($geom/@fme_id)
    EXTRACTED -> GeometryExtractor
Note: extract geometry to assemble it further
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> Counter_2
Note: wall id
Counter_2
    CNT_ATTR = wallID
    DOMAIN = @Value(gml_id)
    SCOPE = Local
    START = 1
    -> GeometryPartExtractor_4

Bookmark: extract lines creating walls
GeometryPartExtractor_4
    GQUERY:
      for $geom in //geometry
      where $geom/@fme_geometry_type = 'IFMELine'
      return number($geom/@fme_id)
    EXTRACTED -> Chopper_2
Chopper_2
    DEAGGREGATE_INPUT = Deaggregate
    MAX_VERTICES = 2
    MODE = By Vertex
    REMNANT_ATTR = _remnant
    CHOPPED -> BoundsExtractor

Bookmark: 2.3.1.2: Split to lines and select lowest line
Note: select lowest line
BoundsExtractor
    ZMAX = LineH
    -> TestFilter_4
TestFilter_4
    DEFAULT_VALUE = <UNFILTERED>
    TEST_LIST:
      "BOOL_OP,AND,COMPOSITE_TEST,""""""1 AND 2"""""",TEST_CLAUSE,TEST @Value(LineH) >= @sub(@Value(minHeight),0.5)
      TEST @Value(LineH) <= @sum(@Value(minHeight),0.5)",lowestLine
    lowestLine -> StringConcatenator_4
Note: create unique id for wall
StringConcatenator_4
    ACTION = Create New Attribute
    PARM_LINE = fme_basicstring:14%1%14:@Value(gml_id)_@Value(wallID)
    VAL_ATTR = wallUniID
    -> LineExtender

Bookmark: 2.3.1.3: Create rectangular buffer - offset
Note: rectanguilar buffer for easier proicessing in surface reconstruction step
Note: to cover "dead angle"
LineExtender
    LEN = @div(@Value(Accuracy),2)
    STRETCHED -> COUNTER1
    STRETCHED -> COUNTER2
    STRETCHED -> COUNTER3
    STRETCHED -> COUNTER1_2
    STRETCHED -> COUNTER2_2
    STRETCHED -> COUNTER3_2
Note: merge both sides
Dissolver_4
    ACCUM_INPUT_ATTRS = Use Attributes From One Feature
    CLEANING_TOLERANCE = Automatic
    CONNECT_Z_MODE = First Wins
    DEAGGREGATE_INPUT = Yes
    GROUP_BY = wallUniID
    AREA -> SpatialRelator [Requestor]
    AREA -> SpatialRelator_3 [Supplier]

Bookmark: one side buffer - left
COUNTER1: Counter
    CNT_ATTR = count
    DOMAIN = counter1
    SCOPE = Global
    START = 0
    -> BUFFERER_4
Note: Buffer the side you DON'T want!
BUFFERER_4: Bufferer
    ANGLE = 22.5
    BUFFSTYLE = RIGHT_SIDE_ONLY
    WIDTH = 2
    BUFFERED -> COMMONSEGMENTFINDER [BASE]
COUNTER2: Counter
    CNT_ATTR = count
    DOMAIN = counter2
    SCOPE = Global
    START = 0
    -> BUFFERER_6
Note: A butt buffer
BUFFERER_6: Bufferer
    ANGLE = 22.5
    BUFFSTYLE = CAP_BUTT
    WIDTH = 2
    BUFFERED -> INTERSECTOR
COUNTER3: Counter
    CNT_ATTR = count
    DOMAIN = counter3
    SCOPE = Global
    START = 0
    -> INTERSECTOR
Note: Intersect buffer and line to / split buffer into left-right sides
INTERSECTOR: Intersector
    DUPLICATE_Z_NODES = No
    GRP_BY = count
    OV_ATTR = overlaps
    SEG_ATTR = _segments
    INTERSECTED -> COMMONSEGMENTFINDER [CANDIDATE]
Note: Throw away the part of the buffer / that matches the side you don't want.
COMMONSEGMENTFINDER: CommonSegmentFinder
    GROUP_BY = count
    NO_OVERLAP -> AreaBuilder_2
AreaBuilder_2
    ALLOW_CYCLES = No
    CHECK_CURVE_DIRECTION = No
    CONNECT_Z_MODE = First Wins
    CONSIDER_NODE_ELEVATION = no
    DEAGGREGATE_INPUT = Deaggregate
    DONUT_CREATION = NO
    GROUP_BY = count
    LINES_AS_SEGMENTS = No
    POLY_ACCUM_ATTRS_NAME = Use Attributes From One Feature
    SNAPTYPE_PARAM = None
    AREA -> Dissolver_4

Bookmark: one side buffer - right
COUNTER1_2: Counter
    CNT_ATTR = count
    DOMAIN = counter1
    SCOPE = Global
    START = 0
    -> BUFFERER_2
Note: Buffer the side you DON'T want!
BUFFERER_2: Bufferer
    ANGLE = 22.5
    BUFFSTYLE = LEFT_SIDE_ONLY
    WIDTH = 2
    BUFFERED -> COMMONSEGMENTFINDER_2 [BASE]
COUNTER2_2: Counter
    CNT_ATTR = count
    DOMAIN = counter2
    SCOPE = Global
    START = 0
    -> BUFFERER_3
Note: A butt buffer
BUFFERER_3: Bufferer
    ANGLE = 22.5
    BUFFSTYLE = CAP_BUTT
    WIDTH = 2
    BUFFERED -> INTERSECTOR_2
COUNTER3_2: Counter
    CNT_ATTR = count
    DOMAIN = counter3
    SCOPE = Global
    START = 0
    -> INTERSECTOR_2
Note: Intersect buffer and line to / split buffer into left-right sides
INTERSECTOR_2: Intersector
    DUPLICATE_Z_NODES = No
    GRP_BY = count
    OV_ATTR = overlaps
    SEG_ATTR = _segments
    INTERSECTED -> COMMONSEGMENTFINDER_2 [CANDIDATE]
Note: Throw away the part of the buffer / that matches the side you don't want.
COMMONSEGMENTFINDER_2: CommonSegmentFinder
    GROUP_BY = count
    NO_OVERLAP -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = NO
    GROUP_BY = count
    LINES_AS_SEGMENTS = No
    POLY_ACCUM_ATTRS_NAME = Use Attributes From One Feature
    SNAPTYPE_PARAM = None
    AREA -> Dissolver_4

Bookmark: 2.1.2.2: Accuracy buffer, 2D & 3D
Respective_Accuracy2D_buffer: Bufferer
    ANGLE = 22.5
    CAP_STYLE = None
    CORNER_STYLE = Arc
    MODE = AREA
    OFFSET = @Value(Accuracy)
    OFFSET_UNITS = NONE
    PRECISION = APPROX
    BUFFERED -> 3DForcer
3DForcer
    KEEPZVAL = No
    ZVALATTR = @Value(PosMH)
    -> Respective_Accuracy3D_buffer
Respective_Accuracy3D_buffer: Extruder
    DIRECTION = Vertical
    DISTANCE = @sum(@Value(RelPosHeight),@Value(Accuracy))
    EXTRUDED -> Clipper [CLIPPER]

Bookmark: 2.2.1: LASTools
Note: -not_airborne flag activated
LAStools.lasground_2
    FME_BASENAME = @Value(fme_basename)
    FME_DATASET = @Value(fme_dataset)
    HORIZONTALUNITS = " "
    ISOLATEDPOINTS = 5
    LASMERGE = Use lastools output
    LASTOOL = D:\projects\PassageFinder\workbench\lookUpWorkbench\LAStools\bin\lasground_new.exe
    LAS_TYPE = @Value(las_type)
    NOISESTEP_XY = 0.5
    NOISESTEP_Z = 0.5
    NONGROUNDCLASSIFICATION = " "
    TERRAIN = -wilderness
    VERTICALUNITS = " "
    GroundClassified -> UniqueClassSplit_3

Bookmark: only NON ground , mapped to class 1 , MLS
Note: only NON ground points used
UniqueClassSplit_3: PointCloudSplitter
    OUTPUT_ATTR = _split_value
    SPLIT_BY_DISPLAY = classification
    SPLIT_TYPE = Unique
    VALUE_LIST = 33,1
    SPLIT -> PointCloudComponentRemover_2
PointCloudComponentRemover_2
    COMPONENTS_TO_REMOVE = classification
    -> MapClasses_2
MapClasses_2: PointCloudComponentAdder
    COMPONENTS_TO_ADD = classification,Int8,"FME_CONDITIONAL:DEFAULT_VALUE'1'BOOL_OP;OR;COMPOSITE_TEST;1 OR 2;TEST @Value(_split_value) = 33;TEST @Value(_split_value) = 1'1'FME_NUM_CONDITIONS2___"
    -> Junction_17
Note: Pass to segmentation
Junction_17
    -> Junction_18

Bookmark: 2.3.1.4: PointCloudDensityCalculator
Note: specific size of the raster
Tiler
    BOUNDARY_CASES = No
    CLEANING_TOLERANCE = Automatic
    COL_ATTR = _column
    GROUP_BY = gml_id
    LINES_AS_SEGMENTS = No
    MEASURE_TYPE = Continuous
    MISSING_VAL_MODE = Compute
    ROW_ATTR = _row
    STARTINGCORNER = Lower Left
    TILING_TYPE = Tile Size
    XINC = 2
    YINC = 2
    TILED -> PointCloudPropertyExtractor
Note: count nr of points within a rectangle
PointCloudPropertyExtractor
    CALCULATE_EXTENTS_DISPLAY = No
    POINT_COMPONENTS = "x    y    z   "
    -> BoundingBoxReplacer
Note: make simple bb of point clouds with attributes
BoundingBoxReplacer
    BOXTYPE = 2D Bounding Box
    BOX -> tmpIDgroup

Bookmark: 2.3.1.5.1: Define which walls should be processed based on input's LoD
tmpIDgroup: AttributeCreator
    ATTR_TABLE = SET_TO groupingTmp = 1
    -> PercentileCalculator
Note: pass patches above the value of 80th percentile
PercentileCalculator
    attribute_perc = _num_points
    group_attr = groupingTmp
    lower_percentile = 5
    upper_percentile = 80
    Top_cut-off -> SpatialRelator [Supplier]
    Top_cut-off -> SpatialRelator_3 [Requestor]
Note: relate patches to walls
SpatialRelator
    AGGREGATE_HANDLING = Yes
    CALC_CARD = No
    CURVE_BOUNDARY_RULE_PARAM = Default Rule
    GROUP_BY = gml_id
    LIST_ATTRS_TO_INCLUDE = _num_points
    LIST_NAME = _relationships
    PREDICATES = CONTAINS INTERSECTS
    SUCCESS_ATTR = _related_candidates
    -> AreaCalculator
AreaCalculator
    AREA_ATTR = wallArea
    AREA_TYPE = Plane Area
    MULT = 1
    -> FeatureMerger_2 [REQUESTOR]
Note: relate walls to patches
SpatialRelator_3
    AGGREGATE_HANDLING = Yes
    CALC_CARD = No
    CURVE_BOUNDARY_RULE_PARAM = Default Rule
    GROUP_BY = gml_id
    LIST_ATTRS_TO_INCLUDE = wallUniID
    LIST_NAME = _relationships
    PREDICATES = CONTAINS INTERSECTS
    SUCCESS_ATTR = _related_candidates
    -> ListExploder_3
ListExploder_3
    ATTR_ACCUM_MODE = Merge List Attributes
    ATTR_CONFLICT_RES = Use List Attribute Values
    INDEX_ATTR = _element_index
    LIST_ATTR = _relationships{}
    ELEMENTS -> AreaCalculator_2
AreaCalculator_2
    AREA_ATTR = patchArea
    AREA_TYPE = Plane Area
    MULT = 1
    -> Aggregator_2
Aggregator_2
    ACCUM_ATTRS_NAME = Use Attributes From One Feature
    AGGREGATE_TYPE = Homogeneous Collection (If Possible)
    GROUP_BY = wallUniID
    MODE = Geometry - Assemble One Level
    SEP = ,
    SUM = patchArea
    AGGREGATE -> GeometryRemover
GeometryRemover
    -> FeatureMerger_2 [SUPPLIER]
FeatureMerger_2
    ATTR_ACCUM_MODE = Merge Supplier
    ATTR_CONFLICT_RES = Use Requestor
    IGNORE_NULLS = No
    JOIN_KEYS = @Value(wallUniID) @Value(wallUniID) AUTO
    MERGE_TYPE = Attributes Only
    PROCESS_DUPS = NO
    REJECT_NULL_MISSING_KEYS = No
    SUPPLIERS_FIRST = No
    MERGED -> percCoverage
percCoverage: AttributeCreator
    ATTR_TABLE = SET_TO percCoverage = @div(@mult(100,@Value(patchArea)),@Value(wallArea))
    -> TestFilter_2
TestFilter_2
    DEFAULT_VALUE = <UNFILTERED>
    TEST_LIST = "BOOL_OP,OR,COMPOSITE_TEST,""""""1"""""",TEST_CLAUSE,TEST @Value(percCoverage) >= 60",>=60
    >=60 -> ListSummer

Bookmark: 2.3.1.5: Check densit of pcl per wall
Note: raster to vector to evaluate density per wall
Note: sum of points per wall
ListSummer
    RESULT = nrPoints
    SRC_LIST = _relationships{}._num_points
    -> StringConcatenator_3
Note: create id for python paths
StringConcatenator_3
    ACTION = Create New Attribute
    PARM_LINE = fme_basicstring:14%1%14:@Value(gml_id)_@Value(wallID)
    VAL_ATTR = pythonPath
    -> AttributeRemover_2
    -> AttributeRemover_4
Note: to ExactMeshCutter
Junction_15
    -> Junction_19
Note: to GeneralMeshCutter
Junction_16
    -> Junction_20

Bookmark: 2.3.1.5.2: Attributes cleaner
Note: clean attr
AttributeRemover_4
    LIST_ATTRS = citygml_address{} citygml_address{}.xlink_href citygml_appearance_member{} citygml_appearance_member{}.xlink_href citygml_appearance{} citygml_appearance{}.xlink_href citygml_auxiliary_traffic_area{} citygml_auxiliary_traffic_area{}.xlink_href citygml_bounded_by{} citygml_bounded_by{}.xlink_href citygml_city_object_member{} citygml_city_object_member{}.xlink_href citygml_consists_of_building_part{} citygml_consists_of_building_part{}.xlink_href citygml_function{} citygml_function{}.codeSpace citygml_generalizes_to{} citygml_generalizes_to{}.xlink_href citygml_interior_building_installation{} citygml_interior_building_installation{}.xlink_href citygml_interior_room{} citygml_interior_room{}.xlink_href citygml_level_of_detail{} citygml_opening{} citygml_opening{}.xlink_href citygml_outer_building_installation{} citygml_outer_building_installation{}.xlink_href citygml_traffic_area{} citygml_traffic_area{}.xlink_href citygml_usage{} citygml_usage{}.codeSpace externalReference{} externalReference{}.externalObject.name externalReference{}.externalObject.uri externalReference{}.informationSystem gml_feature_member{} gml_feature_member{}.xlink_href _relationships{} _relationships{}._label _relationships{}.de9im _relationships{}.pass{}
    REMOVE_ATTRS = Dachneigung,Dachorientierung,DataAvalaible,DatenquelleBodenhoehe,DatenquelleDachhoehe,DatenquelleLage,Flaeche,Gemeindeschluessel,HoeheDach,HoeheGrund,LineH,LoD,Methode,NiedrigsteTraufeDesGebaeudes,PosMH,StandLK,Z_MAX,Z_MAX_ASL,Z_MIN,Z_MIN_ASL,_related_candidates,_remnant,citygml_address,citygml_address{0}.xlink_href,citygml_appearance_member{0}.xlink_href,citygml_appearance{0}.xlink_href,citygml_auxiliary_traffic_area{0}.xlink_href,citygml_bounded_by{0}.xlink_href,citygml_city_object_member{0}.xlink_href,citygml_class,citygml_class_codeSpace,citygml_consists_of_building_part{0}.xlink_href,citygml_creationDate,citygml_crown_diameter,citygml_crown_diameter_units,citygml_feature_role,citygml_feature_role_attr_name,citygml_feature_role_attr_val,citygml_function,citygml_function{0},citygml_function{0}.codeSpace,citygml_generalizes_to{0}.xlink_href,citygml_height,citygml_height_units,citygml_interior_building_installation{0}.xlink_href,citygml_interior_room{0}.xlink_href,citygml_level_of_detail{0},citygml_measured_height,citygml_measured_height_units,citygml_opening{0}.xlink_href,citygml_outer_building_installation{0}.xlink_href,citygml_relative_to_terrain,citygml_relative_to_water,citygml_roof_type,citygml_roof_type_codeSpace,citygml_species,citygml_species_codeSpace,citygml_storey_heights_above_ground,citygml_storey_heights_above_ground_units,citygml_storey_heights_below_ground,citygml_storey_heights_below_ground_units,citygml_storeys_above_ground,citygml_storeys_below_ground,citygml_target_uri,citygml_terminationDate,citygml_traffic_area{0}.xlink_href,citygml_trunk_diameter,citygml_trunk_diameter_units,citygml_usage{0},citygml_usage{0}.codeSpace,citygml_year_of_construction,citygml_year_of_demolition,externalReference{0}.externalObject.name,externalReference{0}.externalObject.uri,externalReference{0}.informationSystem,fme_feature_type,gml_description,gml_feature_member{0}.xlink_href,gml_name,gml_parent_id,opendrive_laneSection_index,opendrive_laneSection_start,opendrive_lane_id,opendrive_lane_level,opendrive_lane_material_friction,opendrive_lane_material_roughness,opendrive_lane_material_surface,opendrive_lane_roadMark_color,opendrive_lane_roadMark_material,opendrive_lane_roadMark_type,opendrive_lane_roadMark_weight,opendrive_lane_speed_max,opendrive_lane_speed_max_units,opendrive_lane_type,opendrive_roadObject_dynamic,opendrive_roadObject_id,opendrive_roadObject_name,opendrive_roadObject_orientation,opendrive_roadObject_type,opendrive_roadObject_validLength,opendrive_roadSignal_countryCode,opendrive_roadSignal_dynamic,opendrive_roadSignal_id,opendrive_roadSignal_name,opendrive_roadSignal_orientation,opendrive_roadSignal_subtype,opendrive_roadSignal_type,opendrive_roadSignal_value,opendrive_road_id,opendrive_road_junction,opendrive_road_length,opendrive_road_rule
    -> Junction_15
    -> Junction_16
AttributeRemover_2
    LIST_ATTRS = citygml_address{} citygml_address{}.xlink_href citygml_appearance_member{} citygml_appearance_member{}.xlink_href citygml_appearance{} citygml_appearance{}.xlink_href citygml_auxiliary_traffic_area{} citygml_auxiliary_traffic_area{}.xlink_href citygml_bounded_by{} citygml_bounded_by{}.xlink_href citygml_city_object_member{} citygml_city_object_member{}.xlink_href citygml_consists_of_building_part{} citygml_consists_of_building_part{}.xlink_href citygml_function{} citygml_function{}.codeSpace citygml_generalizes_to{} citygml_generalizes_to{}.xlink_href citygml_interior_building_installation{} citygml_interior_building_installation{}.xlink_href citygml_interior_room{} citygml_interior_room{}.xlink_href citygml_level_of_detail{} citygml_opening{} citygml_opening{}.xlink_href citygml_outer_building_installation{} citygml_outer_building_installation{}.xlink_href citygml_traffic_area{} citygml_traffic_area{}.xlink_href citygml_usage{} citygml_usage{}.codeSpace externalReference{} externalReference{}.externalObject.name externalReference{}.externalObject.uri externalReference{}.informationSystem gml_feature_member{} gml_feature_member{}.xlink_href _relationships{} _relationships{}._label _relationships{}.de9im _relationships{}.pass{}
    REMOVE_ATTRS = Accuracy,Dachneigung,Dachorientierung,DataAvalaible,DatenquelleBodenhoehe,DatenquelleDachhoehe,DatenquelleLage,Flaeche,Gemeindeschluessel,HoeheDach,HoeheGrund,LineH,LoD,Methode,NiedrigsteTraufeDesGebaeudes,PosMH,RelHeight,StandLK,Z_MAX,Z_MAX_ASL,Z_MIN,Z_MIN_ASL,_geometry,_related_candidates,_remnant,citygml_address,citygml_address{0}.xlink_href,citygml_appearance_member{0}.xlink_href,citygml_appearance{0}.xlink_href,citygml_auxiliary_traffic_area{0}.xlink_href,citygml_bounded_by{0}.xlink_href,citygml_city_object_member{0}.xlink_href,citygml_class,citygml_class_codeSpace,citygml_consists_of_building_part{0}.xlink_href,citygml_creationDate,citygml_crown_diameter,citygml_crown_diameter_units,citygml_feature_role,citygml_feature_role_attr_name,citygml_feature_role_attr_val,citygml_function,citygml_function{0},citygml_function{0}.codeSpace,citygml_generalizes_to{0}.xlink_href,citygml_height,citygml_height_units,citygml_interior_building_installation{0}.xlink_href,citygml_interior_room{0}.xlink_href,citygml_level_of_detail{0},citygml_measured_height,citygml_measured_height_units,citygml_opening{0}.xlink_href,citygml_outer_building_installation{0}.xlink_href,citygml_relative_to_terrain,citygml_relative_to_water,citygml_roof_type,citygml_roof_type_codeSpace,citygml_species,citygml_species_codeSpace,citygml_storey_heights_above_ground,citygml_storey_heights_above_ground_units,citygml_storey_heights_below_ground,citygml_storey_heights_below_ground_units,citygml_storeys_above_ground,citygml_storeys_below_ground,citygml_target_uri,citygml_terminationDate,citygml_traffic_area{0}.xlink_href,citygml_trunk_diameter,citygml_trunk_diameter_units,citygml_usage{0},citygml_usage{0}.codeSpace,citygml_year_of_construction,citygml_year_of_demolition,externalReference{0}.externalObject.name,externalReference{0}.externalObject.uri,externalReference{0}.informationSystem,fme_feature_type,gml_description,gml_feature_member{0}.xlink_href,gml_name,gml_parent_id,minHeight,opendrive_laneSection_index,opendrive_laneSection_start,opendrive_lane_id,opendrive_lane_level,opendrive_lane_material_friction,opendrive_lane_material_roughness,opendrive_lane_material_surface,opendrive_lane_roadMark_color,opendrive_lane_roadMark_material,opendrive_lane_roadMark_type,opendrive_lane_roadMark_weight,opendrive_lane_speed_max,opendrive_lane_speed_max_units,opendrive_lane_type,opendrive_roadObject_dynamic,opendrive_roadObject_id,opendrive_roadObject_name,opendrive_roadObject_orientation,opendrive_roadObject_type,opendrive_roadObject_validLength,opendrive_roadSignal_countryCode,opendrive_roadSignal_dynamic,opendrive_roadSignal_id,opendrive_roadSignal_name,opendrive_roadSignal_orientation,opendrive_roadSignal_subtype,opendrive_roadSignal_type,opendrive_roadSignal_value,opendrive_road_id,opendrive_road_junction,opendrive_road_length,opendrive_road_rule,topHeight
    -> Clipper_3 [CLIPPER]

Bookmark: 2.4.7: Perpendicular offset
Note: from 2d wall buffer
Junction_19
    -> GeometryReplacer
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> ExpressionEvaluator_2
    -> Extruder
ExpressionEvaluator_2
    ACTION = Create New Attribute
    EXPRESSION = -@Value(Accuracy)
    VAL_ATTR = _accuracy
    -> Extruder_2
Extruder_2
    DIRECTION = Auto
    DISTANCE = @div(@Value(_accuracy),2)
    EXTRUDED -> CSGBuilder [A]
Extruder
    DIRECTION = Auto
    DISTANCE = @div(@Value(Accuracy),2)
    EXTRUDED -> CSGBuilder [B]
Note: overlapping geometries, problem (?)
CSGBuilder
    ATTR_ACCUM_MODE = Merge
    ATTR_CONFLICT_RES = Use A
    GROUP_BY = wallUniID
    UNION -> 2DForcer_5
    UNION -> CoordinateSwapper_4

Bookmark: 2.4.8: Step #2, ExactMeshCutter
CoordinateSwapper_4
    SWAP_TYPE = Y <-> Z
    -> 2DForcer_7
2DForcer_7
    2D -> Dissolver_6
Note: simplify clipper
Dissolver_6
    ACCUM_INPUT_ATTRS = Use Attributes From One Feature
    CLEANING_TOLERANCE = Automatic
    CONNECT_Z_MODE = First Wins
    DEAGGREGATE_INPUT = Yes
    GROUP_BY = wallUniID
    AREA -> Clipper_4 [CLIPPER]
Note: swap Y and Z to cut in 2D
CoordinateSwapper_5
    SWAP_TYPE = Y <-> Z
    -> Clipper_4 [CLIPPEE]
Note: group by wallUniqueID
Clipper_4
    BOUNDARY_CASES = Treat as Inside
    CLEANING_TOLERANCE = Automatic
    CLIPPED_ATTR = _clipped
    CLIP_TYPE = Single Clipper
    GROUP_BY = wallUniID
    LINES_AS_SEGMENTS = No
    MEASURE_TYPE = Continuous
    MISSING_VAL_MODE = Compute
    PRESERVE_CLIPPEE_EXTENTS = No
    VAL_SOURCE = Clippee Only
    INSIDE -> CoordinateSwapper_6
Note: back to standard CRS
CoordinateSwapper_6
    SWAP_TYPE = Y <-> Z
    -> AttributeRemover_6
AttributeRemover_6
    REMOVE_ATTRS = RHeight,RelPosHeight,ZminAnd1,_clipped,_geometry_name,_inside_x,_inside_y,_part_number,_related_candidates,fme_basename,fme_dataset,fme_feature_type,gml_name,gml_parent_id,wallID,wallUniID,z.min
    -> GeometryValidator

Bookmark: 2.4.8.1: Relate cutter only to specific walls
2DForcer_5
    2D -> Dissolver_5
Dissolver_5
    ACCUM_INPUT_ATTRS = Use Attributes From One Feature
    CLEANING_TOLERANCE = Automatic
    CONNECT_Z_MODE = First Wins
    DEAGGREGATE_INPUT = Yes
    GROUP_BY = wallUniID
    AREA -> AttributeRemover_5
AttributeRemover_5
    REMOVE_ATTRS = _accuracy,_segments,Accuracy,count,minHeight,nrPoints,overlaps,pythonPath,RelPosHeight,RHeight,topHeight
    -> SpatialRelator_2 [Supplier]
Note: get geometry to set it back later to 3D
GeometryExtractor_2
    ATTR = _quasiMesh
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> 2DForcer_6
Note: flatten to 2D for SpatialRelator
2DForcer_6
    2D -> SpatialRelator_2 [Requestor]
SpatialRelator_2
    AGGREGATE_HANDLING = Yes
    ATTR_ACCUM_MODE = Merge Supplier
    ATTR_CONFLICT_RES = Use Supplier
    CALC_CARD = No
    CURVE_BOUNDARY_RULE_PARAM = Default Rule
    GROUP_BY = gml_id
    PREDICATES = WITHIN INTERSECTS
    SUCCESS_ATTR = _related_candidates
    -> GeometryReplacer_2
Note: set back 3D geometry
GeometryReplacer_2
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_quasiMesh)
    SRS_AXIS_ORDER_DISPLAY = Automatic
    -> CoordinateSwapper_5

Bookmark: 2.4.5: Yield raw walls again
Note: ...to GeneralMeshCutter
Junction_20
    -> Dissolver_3
Note: do NOT distinct for each wall but treat as one building
Dissolver_3
    ACCUM_INPUT_ATTRS = Use Attributes From One Feature
    CLEANING_TOLERANCE = Automatic
    CONNECT_Z_MODE = First Wins
    DEAGGREGATE_INPUT = Yes
    GROUP_BY = gml_id
    AREA -> Generalizer
Generalizer
    ALG_TEXT = Douglas (Generalize)
    PRESERVE = No
    PRESERVE_PATHS = No
    TOLERANCE = 1
    -> 3DForcer_2
3DForcer_2
    KEEPZVAL = No
    ZVALATTR = @Value(minHeight)
    -> Respective_Accuracy3D_buffer_2
Note: use relHeight of a raw model
Respective_Accuracy3D_buffer_2: Extruder
    DIRECTION = Vertical
    DISTANCE = @Value(RHeight)
    EXTRUDED -> CoordinateSwapper

Bookmark: 2.4.6: Step #1, GeneralMeshCutter
CoordinateSwapper
    SWAP_TYPE = Y <-> Z
    -> 2DForcer_4
2DForcer_4
    2D -> Clipper_5 [CLIPPER]
Note: swap Y and Z to cut in 2D
CoordinateSwapper_2
    SWAP_TYPE = Y <-> Z
    -> Clipper_5 [CLIPPEE]
Clipper_5
    BOUNDARY_CASES = Treat as Inside
    CLEANING_TOLERANCE = Automatic
    CLIPPED_ATTR = _clipped
    CLIP_TYPE = Multiple Clippers
    GROUP_BY = gml_id
    LINES_AS_SEGMENTS = No
    MEASURE_TYPE = Continuous
    MISSING_VAL_MODE = Compute
    PRESERVE_CLIPPEE_EXTENTS = No
    VAL_SOURCE = Clippee Only
    INSIDE -> CoordinateSwapper_3
Note: back to standard CRS
CoordinateSwapper_3
    SWAP_TYPE = Y <-> Z
    -> GeometryExtractor_2

Bookmark: 2.3.1.6: PointCloud per each Wall with points
Clipper_3
    ATTR_ACCUM_MODE = Merge Clipper
    ATTR_CONFLICT_RES = Use Clipper
    BOUNDARY_CASES = Treat as Inside
    CLEANING_TOLERANCE = Automatic
    CLIPPED_ATTR = _clipped
    CLIP_TYPE = Multiple Clippers
    GROUP_BY = gml_id
    LINES_AS_SEGMENTS = No
    MEASURE_TYPE = Continuous
    MISSING_VAL_MODE = Compute
    PRESERVE_CLIPPEE_EXTENTS = No
    VAL_SOURCE = Clippee Only
    INSIDE -> FeatureWriter_2 [Output]

Bookmark: 2.3.2.1: Intermediate writer Bld RANSAC
Note: xyz
FeatureWriter_2
    DATASET = $(tmpXYZbld)
    DATASET_ATTR = _dataset
    FEATURE_TYPE_LIST_ATTR = _feature_type
    FORMAT = POINTCLOUDXYZ
    POINTCLOUDXYZ_APPEND = No
    POINTCLOUDXYZ_COLUMN_TO_PCCOMPONENT = x,x,y,y,z,z
    POINTCLOUDXYZ_COORDINATE_SYSTEM_GRANULARITY = FEATURE
    POINTCLOUDXYZ_DESTINATION_DATASETTYPE_VALIDATION = Yes
    POINTCLOUDXYZ_ENCODING = UTF-8
    POINTCLOUDXYZ_EXTENSION = xyz
    POINTCLOUDXYZ_INCLUDE_FIELD_NAME = yes
    POINTCLOUDXYZ_QUOTE_FIELD_NAMES = if_needed
    POINTCLOUDXYZ_QUOTE_OUTPUT = if_needed
    POINTCLOUDXYZ_SEPARATOR = ;
    POINTCLOUDXYZ_WRITE_UTF8_BOM = yes
    TOTAL_FEATURES_WRITTEN_ATTR = _total_features_written
    SUMMARY -> PythonCaller_2

Bookmark: 2.3.2: Pyntcloud integration
Note: RANSAC call
PythonCaller_2
    PYTHONSOURCE:
      import os
      import glob
      from pyntcloud import PyntCloud
      from fmeobjects import (FMELogFile,
                              FME_WARN)#FME native logs


      ####READ####

      #read path as string
      bldXYZ = str(FME_MacroValues['tmpXYZbld'])

      #read, get all xyz files in a directory
      list_walls = [PyntCloud.from_file(files,
                                 sep=";",
                                 header=1,
                                 names=["x","y","z"])
                                 for files in glob.glob (bldXYZ + '\*.xyz')]


      #list of xyz file names
      names_walls = [os.path.basename(x) for x in glob.glob(bldXYZ + '\*.xyz')]

      #get range of elements to iterate on
      index = len(list_walls)

      #fire the RANSAC algorithm
      FMELogFile().logMessageString("#--- The RANSAC algorithm has been triggered... ---#", FME_WARN)

      def ransac(feature):

          for i in range (index):

              ###RANSAC###
              # parameter t in RANSAC
              kwargs = {"max_dist": 0.1}

              is_plane = list_walls[i].add_scalar_field("plane_fit", **kwargs)

              ##select point cloud having only inliers (value==1), so-> not equal 0
              selectInliers = list_walls[i].points.loc[list_walls[i].points["is_plane"] == 1]

              ####WRITE####
              #create directory for output files and check if it exists already
              directoryInliers= str(FME_MacroValues['tmpXYZbldInliers'])

              #create one path
              writing_pathInliers = directoryInliers + '/' + names_walls[i]


              #write selected inliers as csv point cloud
              selectInliers.to_csv(writing_pathInliers, index = False, header=True)
    PYTHONSYMBOL = ransac
    -> ListExploder_2
Note: read RANSAC inliers
FeatureReader_3
    ATTRS_TO_EXPOSE = fme_feature_type
    ATTR_ACCUM_MODE = Merge Initiator and Result
    ATTR_CONFLICT_RES = Use Result
    COMBINE_GEOM = Use Result
    DATASET = @Value(pointcloudXYZnames)
    FORMAT = POINTCLOUDXYZ
    INTERACT = <No Spatial Filter>
    OUTPUT_FEATURES_DISPLAY = Schema and Data Features
    POINTCLOUDXYZ_COLUMN_TO_PCCOMPONENT_HAS_TYPES = yes
    POINTCLOUDXYZ_DUPLICATE_DELIMS = no
    POINTCLOUDXYZ_ENCODING = windows-1252
    POINTCLOUDXYZ_FIELD_NAMES = YES
    POINTCLOUDXYZ_FIELD_NAMES_AFTER_HEADER = no
    POINTCLOUDXYZ_READER_META_ATTRIBUTES = fme_dataset fme_basename
    POINTCLOUDXYZ_SCAN_MAX_LINES = 10000
    POINTCLOUDXYZ_SEPARATOR = auto
    POINTCLOUDXYZ_SKIP_FOOTER = 0
    POINTCLOUDXYZ_SKIP_LINES = 1
    POINTCLOUDXYZ_STRING_DATA_CONTAINS_DELIMS = yes
    POINTCLOUDXYZ_STRIP_QUOTES = no
    POINTCLOUDXYZ_USE_SEARCH_ENVELOPE = NO
    <OTHER> -> StringLengthCalculator

Bookmark: 2.3.2.2: get writing paths and file names
Note: FeatureWriter outputs a / single report feature / where list attribute keeps / the name of the temp LAS file
ListExploder_2
    ATTR_ACCUM_MODE = Prefix Incoming List
    INCOMING_PREFIX = _ransac_
    INDEX_ATTR = _element_index
    LIST_ATTR = _feature_type{}
    LIST_FOUND -> AttributeExposer_2
AttributeExposer_2
    ATTR_LIST = _ransac_name
    -> AttributeCreator_6
AttributeCreator_6
    ATTR_TABLE = SET_TO pathToInliers = $(tmpXYZbldInliers)
    -> StringConcatenator_5
Note: point cloud .xyz paths
StringConcatenator_5
    ACTION = Create New Attribute
    PARM_LINE = fme_basicstring:21%1%20%4:@Value(pathToInliers)\@Value(_ransac_name).xyz
    VAL_ATTR = pointcloudXYZnames
    -> FeatureReader_3 [INITIATOR]

Bookmark: 2.3.2.3: Trim str to gml_id back again
StringLengthCalculator
    LENGTH_ATTR = _length
    SRC_ATTR = _ransac_name
    -> ExpressionEvaluator_3
ExpressionEvaluator_3
    ACTION = Create New Attribute
    EXPRESSION = @sub(@Value(_length),2)
    VAL_ATTR = onlyID
    -> StringLengthFormatter
StringLengthFormatter
    Input_Attr = @Value(_ransac_name)
    RESULT_Attr = gml_id
    StringLength = @Value(onlyID)
    -> AttributeRemover_3
AttributeRemover_3
    REMOVE_ATTRS = _length,fme_basename,fme_feature_type,onlyID
    -> PointCloudCombiner_3

Bookmark: 2.3.2.4: Merge by common building id
Note: merge by gml_id -> object per GML id
PointCloudCombiner_3
    ACCUM_ATTRS_NAME = Yes
    EXTRACT_RASTER_NODATA_NAME = No
    GROUP_BY = gml_id
    SPACING = 1.0
    -> FeatureMerger [REQUESTOR]
    -> LAS_writer [Split]

Bookmark: 2.4.2: intermediate writers
Note: optional LAS writer with global CRS
LAS_writer: FeatureWriter [off]
    DATASET = C:\MasterThesis\Processing\IntermediatePointCloud_1\Road_1
    DATASET_ATTR = _dataset
    FEATURE_TYPE_LIST_ATTR = _feature_type
    FORMAT = LAS
    LAS_COMPRESSION = None
    LAS_COMPUTE_STATISTICS_ON_ARCGIS_LAS_DATASET = No
    LAS_COORDINATE_SYSTEM_GRANULARITY = FEATURE
    LAS_DESTINATION_DATASETTYPE_VALIDATION = Yes
    LAS_VERSION = 1.2
    TOTAL_FEATURES_WRITTEN_ATTR = _total_features_written
FeatureWriter
    DATASET = $(tmpXYZ)
    DATASET_ATTR = _dataset
    FEATURE_TYPE_LIST_ATTR = _feature_type
    FORMAT = POINTCLOUDXYZ
    POINTCLOUDXYZ_APPEND = No
    POINTCLOUDXYZ_COLUMN_TO_PCCOMPONENT = x,x,y,y,z,z
    POINTCLOUDXYZ_COORDINATE_SYSTEM_GRANULARITY = FEATURE
    POINTCLOUDXYZ_DESTINATION_DATASETTYPE_VALIDATION = Yes
    POINTCLOUDXYZ_ENCODING = UTF-8
    POINTCLOUDXYZ_EXTENSION = xyz
    POINTCLOUDXYZ_INCLUDE_FIELD_NAME = yes
    POINTCLOUDXYZ_QUOTE_FIELD_NAMES = if_needed
    POINTCLOUDXYZ_QUOTE_OUTPUT = if_needed
    POINTCLOUDXYZ_SEPARATOR = space
    POINTCLOUDXYZ_WRITE_UTF8_BOM = yes
    TOTAL_FEATURES_WRITTEN_ATTR = _total_features_written
    SUMMARY -> PythonCaller

Bookmark: 2.1.1.3: Extraction of raw center of building
Note: extract raw center of object to ensure orientation of walls in surface reconstruction part
Note: keep only ID
AttributeKeeper
    CREATE_BULK_MODE_FEATURES = No
    KEEP_ATTRS = gml_id
    -> CenterOfBldForLocalCRS
CenterOfBldForLocalCRS: CenterPointExtractor
    CENTX = bldCenterX
    CENTY = bldCenterY
    EXTRACTIONMODE = CENTER
    -> Junction_3

Bookmark: 2.4.1: Move to local crs
Note: Raw single bld position as new CRS origin
Junction_4
    -> FeatureMerger [SUPPLIER]
FeatureMerger
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> PointCloudStatisticsCalculator_2
PointCloudStatisticsCalculator_2
    POINT_COMPONENTS = "z MIN        intensity        "
    -> ExpressionEvaluator
ExpressionEvaluator
    ACTION = Create New Attribute
    EXPRESSION = @sum(@Value(z.min),1)
    VAL_ATTR = ZminAnd1
    -> Offsetter
Offsetter
    MODE = Cartesian Coordinate
    XOFF = -@Value(bldCenterX)
    YOFF = -@Value(bldCenterY)
    ZOFF = -@Value(ZminAnd1)
    OFFSET -> CoordinateSystemRemover
    OFFSET -> GeometryRemover_3
GeometryRemover_3
    -> FeatureMerger_3 [SUPPLIER]
CoordinateSystemRemover
    -> FeatureWriter [Passed]

Bookmark: 2.4.3: MeshLab integration
Note: MeshLab configuration file parser
PythonCaller
    NEW_ATTRIBUTES = _dataset _total_features_written
    PYTHONSOURCE:
      import xml.etree.ElementTree as ET #xml parser
      from fmeobjects import (FMELogFile,
                              FME_WARN)#FME native logs


      FMELogFile().logMessageString("#--- The MXL parser has started: ---#", FME_WARN)
      tree = ET.parse(FME_MacroValues['XMLinput'])
      root = tree.getroot()


      def xmlChanger(feature):

          #Use dictionary index to accesss specific values

          #---------------------------------------------------------------#
          #---Access 'Screened Poisson'---#
          #---------------------------------------------------------------#

          #Set up value for the octree depth
          #default == 12
          octreeDepth = float(root[1][2].get('value')) #take deafult value
          userOctreeDepth = float(FME_MacroValues['userOctreeDepth']) #use input value from user
          strUOD = str(userOctreeDepth)

          #if a value from user is different from the default value then use the user value
          if userOctreeDepth == octreeDepth:
              FMELogFile().logMessageString(' -> Surface Reconstruction: Screened Poisson Octree Depth applied with default value 12')
          else:
              root[1][2].set('value', strUOD)
              FMELogFile().logMessageString(' -> Surface Reconstruction: Screened Poisson Octree Depth applied with value ' + strUOD)


          #---------------------------------------------------------------#
          #---Access 'Simplification: Quadric Edge Collapse Decimation'---#
          #---------------------------------------------------------------#

          #Set up desired number of faces in the end of the simplification process
          #Use it on your own risk! :) -> if this is not known go to the next step
          #default = 1160554
          targetFaceNr = float(root[2][0].get('value'))
          userTargetFaceNr = float(FME_MacroValues['userTargetFace'])
          uTFN = str(userTargetFaceNr)

          if targetFaceNr == userTargetFaceNr:
              FMELogFile().logMessageString(' -> Target number of faces same as default 1160554')
          elif 0 == userTargetFaceNr:
              FMELogFile().logMessageString(' -> Target number of faces NOT applied')
          else:
              root[2][0].set('value', uTFN)
              FMELogFile().logMessageString(' -> Target number of faces applied with value' + uTFN + 'only true if Percentage reduction set to 0')


          #Set up desired percentage of faces in the end of the simplification process
          #Easier for user to estimate only range (0..1)
          targetPerc = float(root[2][1].get('value'))
          userTargetPerc = float(FME_MacroValues['userTargetPerc'])
          uTP = str(userTargetPerc)

          if userTargetPerc == targetPerc:
              FMELogFile().logMessageString(' -> Percentage reduction (0..1) applied with default value')
          elif 0 == userTargetPerc:
              root[2][1].set('value', uTP)
              FMELogFile().logMessageString(' -> Percentage reduction (0..1) NOT applied')
          else:
              root[2][1].set('value', uTP)
              FMELogFile().logMessageString(' -> Percentage reduction (0..1) applied with value ' + uTP)


          #Set up some cleaning to the process, like erasing unreferenced vertices, bad faces, etc.
          #default = true
          #autoClean = bool(root[2][11].get('value'))
          userAutoClean = str(FME_MacroValues['autoClean'])

          if userAutoClean == 'true':
              FMELogFile().logMessageString(' -> Post-simplification cleaning applied')
          else:
              root[2][11].set('value', userAutoClean)
              FMELogFile().logMessageString(' -> Post-simplification cleaning NOT applied')

          #write new mlx
          tree.write(FME_MacroValues['XMLOutput'])

          FMELogFile().logMessageString("#--- The MXL was parsed successfully ---#", FME_WARN)
    PYTHONSYMBOL = xmlChanger
    -> ListExploder
Note: FeatureWriter outputs a single report feature / where list attribute keeps the name of the temp LAS file
ListExploder
    ATTR_ACCUM_MODE = Prefix Incoming List
    INCOMING_PREFIX = _lastools_
    INDEX_ATTR = _element_index
    LIST_ATTR = _feature_type{}
    LIST_FOUND -> AttributeExposer
AttributeExposer
    ATTR_LIST = _lastools_name
    -> StringConcatenator
Note: Create command line attribute
AttributeCreator_4
    ATTR_LIST = meshlabserver_command_line,""$(meshlabserver)" -i "@Value(pointcloudXYZnames)" -o "@Value(surfaceOBJnames)" -s "$(XMLOutput)""
    -> SystemCaller_2
Note: Execute meshlabserver.exe
SystemCaller_2
    ATTR = _exit_code
    CMD = @Value(meshlabserver_command_line)
    -> SuccessOrFailure
SuccessOrFailure: TestFilter
    DEFAULT_VALUE = Failure
    TEST_LIST = BOOL_OP,OR,COMPOSITE_TEST,<Unused>,TEST_CLAUSE,"TEST @Value(_exit_code) = 0",Success
    Success -> FeatureReader [INITIATOR]
    Failure -> Terminator
FeatureReader
    ATTRS_TO_EXPOSE = fme_feature_type
    ATTR_ACCUM_MODE = Only Use Result
    COMBINE_GEOM = Use Result
    DATASET = @Value(surfaceOBJnames)
    FORMAT = OBJ
    INTERACT = <No Spatial Filter>
    OBJ_MERGE_MESH_PARTS = No
    OBJ_MOVE_TO_WORLD_COORDSYS = Yes
    OBJ_USE_SEARCH_ENVELOPE = NO
    OBJ_VARIABLE_FEATURE_TYPES = yes
    OUTPUT_FEATURES_DISPLAY = Schema and Data Features
    <OTHER> -> FeatureMerger_3 [REQUESTOR]
Terminator
    MESSAGE = Translation Terminated. Meshlabserver.exe wasn't executed successfully

Bookmark: get writing paths and file names
Note: point cloud .xyz paths
StringConcatenator
    ACTION = Create New Attribute
    PARM_LINE = fme_basicstring:16%1%22%4:@Value(_dataset)\@Value(_lastools_name).xyz
    VAL_ATTR = pointcloudXYZnames
    -> StringConcatenator_2
Note: reconstructed surface obj paths
StringConcatenator_2
    ACTION = Create New Attribute
    PARM_LINE = fme_basicstring:16%1%22%4:@Value(_dataset)\@Value(_lastools_name).obj
    VAL_ATTR = surfaceOBJnames
    -> AttributeCreator_4

Bookmark: 2.4.4: Reconstructed surface Road clipper to Road extent
FeatureMerger_3
    ATTR_ACCUM_MODE = Merge Supplier
    ATTR_CONFLICT_RES = Use Requestor
    IGNORE_NULLS = No
    JOIN_KEYS = @Value(fme_feature_type) @Value(gml_id) AUTO
    MERGE_TYPE = Attributes Only
    PROCESS_DUPS = NO
    REJECT_NULL_MISSING_KEYS = No
    SUPPLIERS_FIRST = No
    MERGED -> Offsetter_2

Bookmark: 2.4.4.1: Back to original CRS
Offsetter_2
    MODE = Cartesian Coordinate
    XOFF = @Value(bldCenterX)
    YOFF = @Value(bldCenterY)
    ZOFF = @Value(ZminAnd1)
    OFFSET -> CoordinateSystemSetter
CoordinateSystemSetter
    COORDSYS = EPSG:32632
    -> GeometryCoercer

Bookmark: 2.4.4.2: Prepare for clipper
GeometryCoercer
    GQUERY:
      for $geom in //geometry
      where $geom/count(parent::geometry) = 0
      return number($geom/@fme_id)
    KIND = fme_composite_surface
    COERCED -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryCoercer_2
GeometryCoercer_2
    GQUERY:
      for $geom in //geometry
      where $geom/count(parent::geometry) = 0
      return number($geom/@fme_id)
    KIND = fme_polygon
    COERCED -> CoordinateSwapper_2

Bookmark: 2.5.1.1: Geometry repair (in case)
GeometryValidator
    ISSUE_ATTR_NAME = _issues
    PRESETS = Custom
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme SURFACE_ORIENTATION  SOLID_ORIENTATION
    SUMMARY = Detailed
    PASSED -> MultipleGeometryFilter_2
    FAILED -> Counter
    REPAIRED -> MultipleGeometryFilter_2
Note: MultiArea present ("candy" geometry) -> "NotContains"
MultipleGeometryFilter_2
    NOT_CONTAINS -> Deaggregator_4
    <REJECTED> -> AttributeRemover_9
Note: deagg multiareas also from Failed repair
Deaggregator_4
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AttributeRemover_9
AttributeRemover_9
    LIST_ATTRS = _hierarchy_child_id_list{} _issues{} _issues{}.count _issues{}.issue_found _issues{}.location_sample.x _issues{}.location_sample.y _issues{}.location_sample.z
    REMOVE_ATTRS = _geometry_name,_hierarchy_child_id_list{0},_hierarchy_id,_hierarchy_parent_id,_issues{0}.count,_issues{0}.issue_found,_issues{0}.location_sample.x,_issues{0}.location_sample.y,_issues{0}.location_sample.z,_part_number,fme_rejection_code
    -> Orientor

Bookmark: 2.5.1.1.1: Special case repair
Counter
    CNT_ATTR = tmpID
    DOMAIN = counter
    SCOPE = Local
    START = 1
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Dissolver_7
Dissolver_7
    ACCUM_INPUT_ATTRS = Use Attributes From One Feature
    CLEANING_TOLERANCE = Automatic
    CONNECT_Z_MODE = First Wins
    DEAGGREGATE_INPUT = Yes
    GROUP_BY = tmpID
    AREA -> AttributeRemover_7
AttributeRemover_7
    LIST_ATTRS = _issues{} _issues{}.count _issues{}.issue_found _issues{}.location_sample.x _issues{}.location_sample.y _issues{}.location_sample.z _issues{}.repair_state
    REMOVE_ATTRS = _geometry_name,_issues{0}.count,_issues{0}.issue_found,_issues{0}.location_sample.x,_issues{0}.location_sample.y,_issues{0}.location_sample.z,_issues{0}.repair_state,_part_number,tmpID
    -> GeometryValidator_2
GeometryValidator_2
    ISSUE_ATTR_NAME = _issues
    PRESETS = Custom
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme SURFACE_ORIENTATION  SOLID_ORIENTATION
    SUMMARY = Detailed
    PASSED -> MultipleGeometryFilter_2
    FAILED -> in_case_of_error_prompt_message
    REPAIRED -> MultipleGeometryFilter_2
Note: "candy" geometry
in_case_of_error_prompt_message: Terminator [off]
    MESSAGE = Reconstructed Building surface geometry contains error. Check the "Special case repair" bookmark

Bookmark: 2.5.1.2: Swap orientation
Note: in MeshLab center of building is 0,0,0 thus final mesh orientation tend to be oriented towards center (while should be reversed)
Orientor
    FLIP_APPEARANCES_CHOICE = Yes
    KIND = REVERSE
    ORIENTED -> Aggregator_5
Aggregator_5
    ACCUM_ATTRS_NAME = Use Attributes From One Feature
    AGGREGATE_TYPE = Heterogeneous Collection
    COUNT_ATTR = FeaturesNr
    GROUP_BY = gml_id
    MODE = Geometry - Assemble One Level
    SEP = ,
    AGGREGATE -> AddAprioriCityGMLAtt_2 [REQUESTOR]

Bookmark: 2.5.2: Set up geometry and attributes
Note: RAW Buildings LoD1
Junction_26
    -> FeatureMerger_5 [REQUESTOR]
    -> AddAprioriCityGMLAtt_2 [SUPPLIER]
AddAprioriCityGMLAtt_2: FeatureMerger
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> DateTimeStamper_2
AttributeKeeper_2
    CREATE_BULK_MODE_FEATURES = No
    KEEP_ATTRS = HasGeoRefined,citygml_address{0}.xlink_href,citygml_appearance{0}.xlink_href,citygml_bounded_by{0}.xlink_href,citygml_class,citygml_class_codeSpace,citygml_consists_of_building_part{0}.xlink_href,citygml_creationDate,citygml_feature_role,citygml_feature_role_attr_name,citygml_feature_role_attr_val,citygml_function{0},citygml_function{0}.codeSpace,citygml_generalizes_to{0}.xlink_href,citygml_interior_building_installation{0}.xlink_href,citygml_interior_room{0}.xlink_href,citygml_level_of_detail{0},citygml_measured_height,citygml_measured_height_units,citygml_outer_building_installation{0}.xlink_href,citygml_relative_to_terrain,citygml_relative_to_water,citygml_roof_type,citygml_roof_type_codeSpace,citygml_storey_heights_above_ground,citygml_storey_heights_above_ground_units,citygml_storey_heights_below_ground,citygml_storey_heights_below_ground_units,citygml_storeys_above_ground,citygml_storeys_below_ground,citygml_target_uri,citygml_terminationDate,citygml_usage{0},citygml_usage{0}.codeSpace,citygml_year_of_construction,citygml_year_of_demolition,externalReference{0}.externalObject.name,externalReference{0}.externalObject.uri,externalReference{0}.informationSystem,fme_feature_type,gml_description,gml_id,gml_name,gml_parent_id,opendrive_roadObject_dynamic,opendrive_roadObject_id,opendrive_roadObject_name,opendrive_roadObject_orientation,opendrive_roadObject_type,opendrive_road_id,opendrive_road_junction,opendrive_road_length,opendrive_road_rule
    KEEP_LIST = citygml_address{} citygml_address{}.xlink_href citygml_appearance{} citygml_appearance{}.xlink_href citygml_bounded_by{} citygml_bounded_by{}.xlink_href citygml_consists_of_building_part{} citygml_consists_of_building_part{}.xlink_href citygml_function{} citygml_function{}.codeSpace citygml_generalizes_to{} citygml_generalizes_to{}.xlink_href citygml_interior_building_installation{} citygml_interior_building_installation{}.xlink_href citygml_interior_room{} citygml_interior_room{}.xlink_href citygml_level_of_detail{} citygml_outer_building_installation{} citygml_outer_building_installation{}.xlink_href citygml_usage{} citygml_usage{}.codeSpace externalReference{} externalReference{}.externalObject.name externalReference{}.externalObject.uri externalReference{}.informationSystem
    -> GeometryValidator_3
    -> GeometryRemover_2

Bookmark: 2.5.2.1: Add date CityGML-like
DateTimeStamper_2
    DATETIME_ATTR = Timestamp
    STAMP_TYPE = date
    TIMEZONE = utc
    -> DateTimeConverter_2
DateTimeConverter_2
    DATETIME_ATTR = Timestamp
    OUT_FORMAT = %Y-%m-%d
    PASSTHROUGH = NO
    REPAIR_INPUT = YES
    -> AttributeRemover_8
    -> AttributeRemover_10

Bookmark: 2.5.2.1 Make raw buildings as parts in Lod2
AttributeRemover_10
    LIST_ATTRS = _issues{} _issues{}.count _issues{}.issue_found _issues{}.location_sample.x _issues{}.location_sample.y _issues{}.location_sample.z citygml_address{} citygml_address{}.xlink_href citygml_appearance_member{} citygml_appearance_member{}.xlink_href citygml_appearance{} citygml_appearance{}.xlink_href citygml_auxiliary_traffic_area{} citygml_auxiliary_traffic_area{}.xlink_href citygml_bounded_by{} citygml_bounded_by{}.xlink_href citygml_city_object_member{} citygml_city_object_member{}.xlink_href citygml_consists_of_building_part{} citygml_consists_of_building_part{}.xlink_href citygml_function{} citygml_function{}.codeSpace citygml_generalizes_to{} citygml_generalizes_to{}.xlink_href citygml_interior_building_installation{} citygml_interior_building_installation{}.xlink_href citygml_interior_room{} citygml_interior_room{}.xlink_href citygml_level_of_detail{} citygml_opening{} citygml_opening{}.xlink_href citygml_outer_building_installation{} citygml_outer_building_installation{}.xlink_href citygml_traffic_area{} citygml_traffic_area{}.xlink_href citygml_usage{} citygml_usage{}.codeSpace externalReference{} externalReference{}.externalObject.name externalReference{}.externalObject.uri externalReference{}.informationSystem gml_feature_member{} gml_feature_member{}.xlink_href
    REMOVE_ATTRS = Accuracy,LoD,PosMH,RHeight,RelPosHeight,minHeight,topHeight,citygml_address{0}.xlink_href,citygml_appearance{0}.xlink_href,citygml_bounded_by{0}.xlink_href,citygml_class,citygml_class_codeSpace,citygml_consists_of_building_part{0}.xlink_href,citygml_creationDate,citygml_feature_role,citygml_feature_role_attr_name,citygml_feature_role_attr_val,citygml_function{0},citygml_function{0}.codeSpace,citygml_generalizes_to{0}.xlink_href,citygml_interior_building_installation{0}.xlink_href,citygml_interior_room{0}.xlink_href,citygml_level_of_detail{0},citygml_measured_height,citygml_measured_height_units,citygml_outer_building_installation{0}.xlink_href,citygml_relative_to_terrain,citygml_relative_to_water,citygml_roof_type,citygml_roof_type_codeSpace,citygml_storey_heights_above_ground,citygml_storey_heights_above_ground_units,citygml_storey_heights_below_ground,citygml_storey_heights_below_ground_units,citygml_storeys_above_ground,citygml_storeys_below_ground,citygml_target_uri,citygml_terminationDate,citygml_usage{0},citygml_usage{0}.codeSpace,citygml_year_of_construction,citygml_year_of_demolition,externalReference{0}.externalObject.name,externalReference{0}.externalObject.uri,externalReference{0}.informationSystem,fme_feature_type,gml_description,gml_name,gml_parent_id,opendrive_roadObject_dynamic,opendrive_roadObject_id,opendrive_roadObject_name,opendrive_roadObject_orientation,opendrive_roadObject_type,opendrive_road_id,opendrive_road_junction,opendrive_road_length,opendrive_road_rule,FeaturesNr,Timestamp,_ransac_count,_ransac_name,_dataset,_element_index,_total_features_written,bldCenterX,bldCenterY,pathToInliers,pointcloudXYZnames
    -> FeatureMerger_5 [SUPPLIER]
FeatureMerger_5
    ATTR_ACCUM_MODE = Merge Supplier
    ATTR_CONFLICT_RES = Use Requestor
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> AttributeCreator_3
    UNMERGED_REQUESTOR -> AttributeCreator_5
Note: Add HasGeoRefined True OR False
AttributeCreator_3
    ATTR_TABLE = SET_TO HasGeoRefined = True
    -> AttributeKeeper_2
AttributeCreator_5
    ATTR_TABLE = SET_TO HasGeoRefined = False
    -> AttributeKeeper_2

Bookmark: 2.5.2.2 Building to Building in LoD2
Note: Create surface normals
GeometryValidator_3
    MISSING_VERTEX_NORMALS = MISSING_VERTEX_NORMALS
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = None
    PASSED -> GeometryPropertySetter
    REPAIRED -> GeometryPropertySetter
Note: Set a counter trait on each / face for unique face id
GeometryPropertySetter
    CNT_ATTR = _count
    DOMAIN = counter
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor_5
Note: Extract faces from brep
GeometryPartExtractor_5
    EXTRACTTYPE_PARAM = Extract
    GQUERY:
      for $geom in //geometry
      where $geom/@fme_geometry_type = 'IFMEFace'
      return number($geom/@fme_id)
    PROCESSED -> GeometryPropertyExtractor
Note: Extract face id to attribute
GeometryPropertyExtractor
    EXTRACTTYPE_PARAM = Traits
    PREFIX_EXTRACTED_TRAITS = No
    TRAIT_ATTR_LIST = _count,No
    EXTRACTED -> GeometryPartExtractor_2
Note: Extract polygon from face
GeometryPartExtractor_2
    EXTRACTTYPE_PARAM = Extract
    GQUERY:
      for $geom in //geometry
      where $geom/@fme_geometry_type = 'IFMEPolygon'
      return number($geom/@fme_id)
    PROCESSED -> MeasureExtractor_2
Note: Get z normal of polygon
MeasureExtractor_2
    GEOM_TYPE = Individual Vertex by Index
    INDEX = 0
    MEASURE_ATTR = _normal_z
    MEASURE_NAME = fme_vertex_normal_z
    -> TestFilter_6
Note: Separate ground, roof and / wall faces by z normal value
TestFilter_6
    DEFAULT_VALUE = Wall
    TEST_LIST = "BOOL_OP,AND,COMPOSITE_TEST,""""""1"""""",TEST_CLAUSE,TEST @Value(_normal_z) <= -0.5",Ground,"BOOL_OP,OR,COMPOSITE_TEST,""""""1"""""",TEST_CLAUSE,TEST @Value(_normal_z) >= 0.1",Roof
    Ground -> AttributeCreator_9
    Roof -> AttributeCreator_8
    Wall -> AttributeCreator_7
AttributeCreator_9
    ATTR_TABLE = SET_TO name = GroundSurface
    -> Junction_36
AttributeCreator_8
    ATTR_TABLE = SET_TO name = RoofSurface
    -> Junction_36
AttributeCreator_7
    ATTR_TABLE = SET_TO name = WallSurface
    -> Junction_36
GeometryRemover_2
    -> Building (writer CITYGML_3)

Bookmark: Walls, Roofs etc. Set corresponding attributes
Junction_36
    -> AttributeExposer_3
Note: expose id of a building
AttributeExposer_3
    ATTR_LIST = gml_id
    -> AttributeKeeper_5

Bookmark: new uniqueID and link to Bld
Note: only name and id
AttributeKeeper_5
    CREATE_BULK_MODE_FEATURES = NO
    KEEP_ATTRS = name,gml_id
    -> AttributeRenamer_2
AttributeRenamer_2
    ATTR_TABLE = RENAME_SET_DEFAULT gml_id > gml_parent_id
    -> UUIDGenerator_2
UUIDGenerator_2
    UUID_ATTR = _uuid
    -> StringConcatenator_7
StringConcatenator_7
    ACTION = Create New Attribute
    PARM_LINE = fme_basicstring:21%1%13:@Value(gml_parent_id)_@Value(_uuid)
    VAL_ATTR = gml_id
    -> AttributeKeeper_8

Bookmark: Respective geometry and others
AttributeKeeper_8
    CREATE_BULK_MODE_FEATURES = NO
    KEEP_ATTRS = gml_id,gml_parent_id,name
    -> CityGMLGeometrySetter_3
Note: set building
CityGMLGeometrySetter_3
    GEOM = lod2MultiSurface
    ROLE = boundedBy
    -> CityGMLSemSetter
CityGMLSemSetter: TestFilter
    DEFAULT_VALUE = <UNFILTERED>
    TEST_LIST = "BOOL_OP,OR,COMPOSITE_TEST,""""""1"""""",TEST_CLAUSE,TEST @Value(name) = GroundSurface",GroundSurface,"BOOL_OP,OR,COMPOSITE_TEST,""""""1"""""",TEST_CLAUSE,TEST @Value(name) = RoofSurface",RoofSurface,"BOOL_OP,OR,COMPOSITE_TEST,""""""1"""""",TEST_CLAUSE,TEST @Value(name) = WallSurface",WallSurface
    GroundSurface -> GroundSurface (writer CITYGML_3)
    RoofSurface -> RoofSurface (writer CITYGML_3)
    WallSurface -> WallSurface (writer CITYGML_3)

Bookmark: 3.1.1: Buildings
GroundSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
RoofSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
Building (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_year_of_construction xml_buffer, citygml_year_of_demolition xml_buffer, citygml_roof_type xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer,
      citygml_level_of_detail{} xml_buffer, citygml_interior_room{}.xlink_href xml_buffer, citygml_consists_of_building_part{}.xlink_href xml_buffer, citygml_address{}.xlink_href xml_buffer
WallSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer, Timestamp xml_buffer, FeaturesNo xml_buffer

Bookmark: 2.5.2.3: Refined walls to Walls in LoD3
AttributeRemover_8
    LIST_ATTRS = _issues{} _issues{}.count _issues{}.issue_found _issues{}.location_sample.x _issues{}.location_sample.y _issues{}.location_sample.z citygml_address{} citygml_address{}.xlink_href citygml_appearance_member{} citygml_appearance_member{}.xlink_href citygml_appearance{} citygml_appearance{}.xlink_href citygml_auxiliary_traffic_area{} citygml_auxiliary_traffic_area{}.xlink_href citygml_bounded_by{} citygml_bounded_by{}.xlink_href citygml_city_object_member{} citygml_city_object_member{}.xlink_href citygml_consists_of_building_part{} citygml_consists_of_building_part{}.xlink_href citygml_function{} citygml_function{}.codeSpace citygml_generalizes_to{} citygml_generalizes_to{}.xlink_href citygml_interior_building_installation{} citygml_interior_building_installation{}.xlink_href citygml_interior_room{} citygml_interior_room{}.xlink_href citygml_level_of_detail{} citygml_opening{} citygml_opening{}.xlink_href citygml_outer_building_installation{} citygml_outer_building_installation{}.xlink_href citygml_traffic_area{} citygml_traffic_area{}.xlink_href citygml_usage{} citygml_usage{}.codeSpace externalReference{} externalReference{}.externalObject.name externalReference{}.externalObject.uri externalReference{}.informationSystem gml_feature_member{} gml_feature_member{}.xlink_href
    REMOVE_ATTRS = Accuracy,LoD,PosMH,RHeight,RelPosHeight,_overlaps,minHeight,topHeight,Dachneigung,Dachorientierung,DataAvalaible,DatenquelleBodenhoehe,DatenquelleDachhoehe,DatenquelleLage,Flaeche,Gemeindeschluessel,HoeheDach,HoeheGrund,Methode,NiedrigsteTraufeDesGebaeudes,StandLK,Z_MAX,Z_MAX_ASL,Z_MIN,Z_MIN_ASL,citygml_address,citygml_address{0}.xlink_href,citygml_appearance_member{0}.xlink_href,citygml_appearance{0}.xlink_href,citygml_auxiliary_traffic_area{0}.xlink_href,citygml_bounded_by{0}.xlink_href,citygml_city_object_member{0}.xlink_href,citygml_class,citygml_class_codeSpace,citygml_consists_of_building_part{0}.xlink_href,citygml_creationDate,citygml_crown_diameter,citygml_crown_diameter_units,citygml_feature_role,citygml_feature_role_attr_name,citygml_feature_role_attr_val,citygml_function,citygml_function{0},citygml_function{0}.codeSpace,citygml_generalizes_to{0}.xlink_href,citygml_height,citygml_height_units,citygml_interior_building_installation{0}.xlink_href,citygml_interior_room{0}.xlink_href,citygml_level_of_detail{0},citygml_measured_height,citygml_measured_height_units,citygml_opening{0}.xlink_href,citygml_outer_building_installation{0}.xlink_href,citygml_relative_to_terrain,citygml_relative_to_water,citygml_roof_type,citygml_roof_type_codeSpace,citygml_species,citygml_species_codeSpace,citygml_storey_heights_above_ground,citygml_storey_heights_above_ground_units,citygml_storey_heights_below_ground,citygml_storey_heights_below_ground_units,citygml_storeys_above_ground,citygml_storeys_below_ground,citygml_target_uri,citygml_terminationDate,citygml_traffic_area{0}.xlink_href,citygml_trunk_diameter,citygml_trunk_diameter_units,citygml_usage{0},citygml_usage{0}.codeSpace,citygml_year_of_construction,citygml_year_of_demolition,externalReference{0}.externalObject.name,externalReference{0}.externalObject.uri,externalReference{0}.informationSystem,fme_feature_type,gml_description,gml_feature_member{0}.xlink_href,gml_name,gml_parent_id,opendrive_laneSection_index,opendrive_laneSection_start,opendrive_lane_id,opendrive_lane_level,opendrive_lane_material_friction,opendrive_lane_material_roughness,opendrive_lane_material_surface,opendrive_lane_roadMark_color,opendrive_lane_roadMark_material,opendrive_lane_roadMark_type,opendrive_lane_roadMark_weight,opendrive_lane_speed_max,opendrive_lane_speed_max_units,opendrive_lane_type,opendrive_roadObject_dynamic,opendrive_roadObject_id,opendrive_roadObject_name,opendrive_roadObject_orientation,opendrive_roadObject_type,opendrive_roadObject_validLength,opendrive_roadSignal_countryCode,opendrive_roadSignal_dynamic,opendrive_roadSignal_id,opendrive_roadSignal_name,opendrive_roadSignal_orientation,opendrive_roadSignal_subtype,opendrive_roadSignal_type,opendrive_roadSignal_value,opendrive_road_id,opendrive_road_junction,opendrive_road_length,opendrive_road_rule
    -> AttributeRenamer_3
Note: gml_id to gml_parent_id, as a link to particular Bld / FeaturesNr to FeatureNo
AttributeRenamer_3
    ATTR_TABLE:
      RENAME_SET_DEFAULT gml_id > gml_parent_id
      RENAME_SET_DEFAULT FeaturesNr > FeaturesNo
    -> UUIDGenerator
Note: new unique gml_id for each feature
UUIDGenerator
    UUID_ATTR = gml_id
    -> StringConcatenator_6
Note: add string prefix to id
StringConcatenator_6
    ACTION = Overwrite Existing Attributes
    ATTRLIST = gml_id
    PARM_LINE = fme_basicstring:7%14:Refine_@Value(gml_id)
    -> CityGMLGeometrySetter
CityGMLGeometrySetter
    GEOM = lod3MultiSurface
    ROLE = boundedBy
    -> AttributeKeeper_3
AttributeKeeper_3
    CREATE_BULK_MODE_FEATURES = NO
    KEEP_ATTRS = citygml_feature_role,citygml_lod_name,gml_id,gml_parent_id,Timestamp,FeaturesNo
    -> DuplicateFilter_3
Note: in case of any redundant reconstructions
DuplicateFilter_3
    INPUT_ORDERED_CHOICE = No
    KEYATTR = gml_parent_id
    UNIQUE -> WallSurface (writer CITYGML_3)

Bookmark: 2.2: Ground Points Filtering
Note: 33 - non-ground (1) / 34 - ground (2)

Bookmark: 2.4: Surface Reconstruction
Note: normalize the point cloud before export / ATTENTION, not shifted to 0 but 1m below zero! Because of MeshLab

FME custom transformer StringLengthFormatter
Formats attributes to the specified length either truncating or padding the incoming attributes. 
For example, if you set the String Length parameter to 5:
    If an input attribute value consists of only 3 characters, this transformer will add two spaces to the end of the attribute value
    If an input attribute value has a length of 7, this transformer will remove two characters from the end of it
Parameters
    String Length
The desired length of the string to output.
    Source Attribute
Specify the attribute containing the string to reformat.
    Destination Attribute
Specify the name of the attribute to store the reformatted string.

Parameters:
- StringLength = 5   # String length
- Input_Attr =   # Source Attribute
- RESULT_Attr =   # TYPE:varchar(200) Destination Attribute

Input (input)
    -> ParameterFetcher
Note: Retrieve parameters
ParameterFetcher
    ATTR_LIST = _slfLength {$(StringLength)} _slfSource {$(Input_Attr)}
    -> StringLengthCalculator
Note: Determine the input string's length
StringLengthCalculator
    LENGTH_ATTR = _slfSourceLength
    SRC_ATTR = _slfSource
    -> Tester
Note: Check whether input / string is longer than / user's chosen length
Tester
    BOOL_OP = OR
    TEST_CLAUSE = TEST @Value(_slfSourceLength) > @Value(_slfLength)
    TEST_MODE = Automatic
    PASSED -> ExpressionEvaluator
    FAILED -> AttributeCreator
Note: Clean up
AttributeRemover
    REMOVE_ATTRS = $(RESULT_Attr),_slfLength,_slfSource,_slfSourceshrt,_slfSourceLength
    -> Output (output)
Output (output)

Bookmark: If string is longer, remove the extra characters
ExpressionEvaluator
    ACTION = Create New Attribute
    EXPRESSION = @Value(_slfLength)-1
    VAL_ATTR = _slfLength
    -> SubstringExtractor
SubstringExtractor
    END = @Value(_slfLength)
    RESULT_ATTR = $(RESULT_Attr)
    SRC_STRING = @Value(_slfSource)
    START = 0
    -> AttributeRemover

Bookmark: If string is shorter, add extra spaces to the end
AttributeCreator
    ATTR_TABLE = SET_TO $(RESULT_Attr) = @Value(_slfSource)
    -> StringPadder
StringPadder
    BLANK_ATTRIBUTE = Yes
    PADCHAR = " "
    SIDE = Right
    SRC_ATTRS = $(RESULT_Attr)
    WIDTH = @Value(_slfLength)
    -> AttributeRemover

FME custom transformer PercentileCalculator
Calculates upper and lower percentiles of numeric data stored in an attribute.
Description 
A percentile is a statistical measure that marks the value below which a given  percentage  of observations in a set of observations falls. 
This transformer provides a chance to set and calculate upper and lower percentiles for a given numeric dataset that is held in an attribute.
Usage 
Input port 
Input is the data stored in one attribute containing a range of numeric data. 
Parameters 
Select attribute - an attribute in an input dataset. 
Group by - an attribute which may be used to group features and perform percentile calculation per individual group of features. 
Upper percentile - percentile value that is used to indicate and cut off top part of observations in the dataset. 
Lower percentile - percentile value that is used to indicate and cut off bottom part of observations in the dataset. 
Output Ports 
Summary
Body_set
Top_cut-off
Bottom_cut-off
Rejected

Parameters:
- attribute_perc =   # "" Select attribute
- group_attr =   # " " Group by
- upper_percentile = 95   # Upper percentile
- lower_percentile = 5   # Lower percentile

Input (input)
    -> AttributeCreator
AttributeCreator
    ATTR_TABLE:
      SET_TO Percentile_attr = @Value($(attribute_perc))
      SET_TO Sort_attr = @Value($(group_attr))
    -> Tester
Tester
    BOOL_OP = OR
    COMPOSITE_TEST = 1
    TEST_CLAUSE = TEST @Value(Percentile_attr) TYPE NUM
    TEST_MODE = TEST
    PASSED -> Sorter
    FAILED -> Junction
Sorter
    GROUP_BY = Sort_attr
    SORT_PARM = Percentile_attr NUMERIC ASCENDING
    SORTED -> Counter
Counter
    CNT_ATTR = _member
    DOMAIN = @Value(Sort_attr)
    SCOPE = Local
    START = 1
    -> FeatureMerger [REQUESTOR]
    -> Aggregator
    <REJECTED> -> Junction
Aggregator
    ACCUM_ATTRS_NAME = Merge Incoming Attributes
    AGGREGATE_TYPE = Homogeneous Collection (If Possible)
    COUNT_ATTR = Count_agg
    GROUP_BY = Sort_attr
    MODE = Geometry - Assemble One Level
    SEP = ,
    AGGREGATE -> ExpressionEvaluator_4
ExpressionEvaluator_4
    ACTION = Create New Attribute
    EXPRESSION = ($(upper_percentile)/(100))*@Value(Count_agg)
    VAL_ATTR = _upperPercentile
    -> ExpressionEvaluator_2
ExpressionEvaluator_2
    ACTION = Create New Attribute
    EXPRESSION = ($(lower_percentile)/100)*@Value(Count_agg)
    VAL_ATTR = _lowerPercentile
    -> AttributeRounder
AttributeRounder
    PLACES = 0
    ROUND_TYPE = Up
    SRC_ATTRS = _lowerPercentile _upperPercentile
    -> FeatureMerger [SUPPLIER]
FeatureMerger
    ATTR_ACCUM_MODE = Merge Supplier
    ATTR_CONFLICT_RES = Use Requestor
    IGNORE_NULLS = No
    JOIN_KEYS = @Value(Sort_attr) @Value(Sort_attr) AUTO
    MERGE_TYPE = Attributes Only
    PROCESS_DUPS = NO
    REJECT_NULL_MISSING_KEYS = No
    SUPPLIERS_FIRST = No
    MERGED -> TestFilter
    <REJECTED> -> Junction
TestFilter
    DEFAULT_VALUE = <UNFILTERED>
    TEST_LIST = "BOOL_OP,OR,COMPOSITE_TEST,""""""1"""""",TEST_CLAUSE,TEST @Value(_member) > @Value(_upperPercentile)",Top cut-off,"BOOL_OP,OR,COMPOSITE_TEST,""""""1"""""",TEST_CLAUSE,TEST @Value(_member) <= @Value(_lowerPercentile)",Bottom cut-off,"BOOL_OP,OR,COMPOSITE_TEST,""""""1"""""",TEST_CLAUSE,NUM_TEST @Value(_member) RANGE [@Evaluate(@Value(_lowerPercentile)),@Evaluate(@Value(_upperPercentile))]",Body
    Top cut-off -> AttributeRemover_2
    Bottom cut-off -> AttributeRemover
    Body -> AttributeRemover_3
    Body -> StatisticsCalculator
StatisticsCalculator
    COMPUTE_HISTOGRAM = NO
    GROUP_BY = Sort_attr
    MAX_ATTR = _max
    MIN_ATTR = _min
    PREPEND_ATTR_NAME_CHOICE = For multiple results only
    STATS_ATTRS = Percentile_attr
    SUMMARY -> AttributeRenamer
AttributeRenamer
    ATTR_TABLE:
      RENAME_SET_DEFAULT Percentile_attr.min > Lower_percentile
      RENAME_SET_DEFAULT Percentile_attr.max > Upper_percentile
    -> Summary (output)
Summary (output)
AttributeRemover_3
    REMOVE_ATTRS = _lowerPercentile,_upperPercentile,Count_agg,Percentile_attr,Sort_attr
    -> Body_set (output)
Body_set (output)
AttributeRemover_2
    REMOVE_ATTRS = _lowerPercentile,_upperPercentile,Count_agg,Percentile_attr,Sort_attr
    -> Top_cut-off (output)
Top_cut-off (output)
AttributeRemover
    REMOVE_ATTRS = _lowerPercentile,_upperPercentile,Count_agg,Percentile_attr,Sort_attr
    -> Bottom_cut-off (output)
Bottom_cut-off (output)
Junction
    -> Rejected (output)
Rejected (output)

FME custom transformer LAStools.lasground
LAStools.lasground is a wrapper transformer for lasground.exe, a tool from LAStools software suite (www.rapidlasso.com).
Safe Software does not ship LAStools suite and does not provide support for its components. With problem regarding the wrapper transformer contact support@safe.com.
lasground.exe is a tool for bare-earth extraction: it classifies the LiDAR points into ground points (class = 2) and non-ground points (class = 1).
    See lasground documentation for more details and available options:
https://www.cs.unc.edu/~isenburg/lastools/download/lasground_README.txt
Make sure LAStools software suite is installed.
Specify the path to lasground_new.exe.
Refer to https://www.cs.unc.edu/~isenburg/lastools/download/lasground_README.txt for more information.

Parameters:
- LASTOOL = C:\Program Files\LAStools\bin\lasground_new.exe   # Lasground_new.exe location
- TERRAIN = -city   # or hills,-nature%Towns or flats,-town%City or warehouses,-city%Metropolis,-metro Terrain type
- NONGROUNDCLASSIFICATION = -non_ground_unchanged
- HORIZONTALUNITS =   # Meters, %Feet,-feet Horizontal units
- VERTICALUNITS =   # Meters, %Feet,-elevation_feet Vertical units
- NOISESTEP_XY = 4   # Cell size in XY
- NOISESTEP_Z = 4   # Cell size along Z
- ISOLATEDPOINTS = 5   # Number of isolated points in 3x3x3 array of cells
- LASMERGE = Use lastools output   # "Use lastools output"%"Merge with the source" Lastools output handling (LAS components only)
- FME_BASENAME = @Value(fme_basename)   # Fme Basename
- FME_DATASET = @Value(fme_dataset)   # Fme Dataset
- LAS_TYPE = @Value(las_type)   # Las Type

PointCloud (input)
    -> TclCaller_2
FilenamePartExtractor
    DIRNAME_ATTR = _dirname
    DIRPATH_ATTR = _dirpath
    EXTENSION_ATTR = _extension
    FULLNAME_ATTR = _filename
    ROOTNAME_ATTR = _rootname
    SRC_ATTR = @Value(_lastools_temp_input)
    -> FMEFunctionCaller
Note: @ExtractPointCloudProperties(MODIFICATION_PROPERTIES) / Adds three attributes: / _source_format / _source_dataset / _modified / The last one allows to tell whether the LAS file was changed after reading
FMEFunctionCaller
    FUNC = @ExtractPointCloudProperties(MODIFICATION_PROPERTIES)
    -> AttributeExposer_2
AttributeExposer_2
    ATTR_LIST = _modified,_source_format
    -> TestFilter
    -> FeatureMerger_2 [SUPPLIER]
TestFilter
    DEFAULT_VALUE = No direct LAS processing
    TEST_LIST:
      BOOL_OP,AND,COMPOSITE_TEST,<Unused>,TEST_CLAUSE,"TEST @Value(_source_format) = LAS
      TEST @Value(_modified) = No",Direct LAS processing
    Direct LAS processing -> AttributeCreator_2
    Direct LAS processing -> PointCloudMerger [REQUESTOR]
    No direct LAS processing -> FeatureWriter [Output]
    No direct LAS processing -> FeatureMerger [REQUESTOR]
    No direct LAS processing -> PointCloudMerger [REQUESTOR]
Note: Save point clouds as LAS in temp folder
FeatureWriter
    DATASET = @Value(_dirpath)
    DATASET_ATTR = _dataset
    FEATURE_TYPE_LIST_ATTR = _feature_type
    FORMAT = LAS
    LAS_COMPRESSION = None
    LAS_COORDINATE_SYSTEM_GRANULARITY = FEATURE
    LAS_DESTINATION_DATASETTYPE_VALIDATION = Yes
    LAS_VERSION = 1.4
    TOTAL_FEATURES_WRITTEN_ATTR = _total_features_written
    WRITER_DIRECTIVES = VERSION,1.4,COMPRESSION,None,DESTINATION_DATASETTYPE_VALIDATION,Yes,COORDINATE_SYSTEM_GRANULARITY,FEATURE
    SUMMARY -> ListExploder
Note: FeatureWriter outputs a single report feature / where list attribute keeps the name of the temp LAS file
ListExploder
    ATTR_ACCUM_MODE = Prefix Incoming List
    INCOMING_PREFIX = _lastools_
    INDEX_ATTR = _element_index
    LIST_ATTR = _feature_type{}
    LIST_FOUND -> AttributeExposer
AttributeExposer
    ATTR_LIST = _lastools_name
    -> FeatureMerger [SUPPLIER]
Note: We need FileWriter to finish saving temp LAS files before sending command to LAStools. / This transformer guarantees this by waiting a summary feature
FeatureMerger
    ATTR_ACCUM_MODE = Merge Supplier
    ATTR_CONFLICT_RES = Use Requestor
    IGNORE_NULLS = No
    JOIN_KEYS = @Value(_rootname) @Value(_lastools_name) AUTO
    MERGE_TYPE = Attributes Only
    PROCESS_DUPS = No
    SUPPLIERS_FIRST = No
    MERGED -> AttributeCreator_2
Note: Create command line attribute
AttributeCreator_2
    ATTR_LIST = _lastools_command_line,"FME_CONDITIONAL:DEFAULT_VALUE'""$(LASTOOL)" -i "@Value(_lastools_temp_input)" -o "@Value(_lastools_temp_output)" $(TERRAIN) $(NONGROUNDCLASSIFICATION) $(HORIZONTALUNITS) $(VERTICALUNITS) -cores 16 -not_airborne"'BOOL_OP;AND;COMPOSITE_TEST;<Unused>;TEST @Value(_source_format) = LAS;TEST @Value(_modified) = No'""$(LASTOOL)" -i "@Value(fme_dataset)" -o "@Value(_lastools_temp_output)" $(TERRAIN) $(NONGROUNDCLASSIFICATION) $(HORIZONTALUNITS) $(VERTICALUNITS) -cores 16 -not_airborne"'FME_NUM_CONDITIONS2___"
    -> SystemCaller_2
Note: Execute lastools lasground
SystemCaller_2
    ATTR = _exit_code
    CMD = @Value(_lastools_command_line)
    -> TestFilter_2
Note: If lastools finished successfully, / pass features further, / otherwise, terminate the translation
TestFilter_2
    DEFAULT_VALUE = Failure
    TEST_LIST = BOOL_OP,OR,COMPOSITE_TEST,<Unused>,TEST_CLAUSE,"TEST @Value(_exit_code) = 0",Success
    Success -> FeatureReader [INITIATOR]
    Failure -> Terminator
Note: Read back features from temp folder with results
FeatureReader
    ATTRS_TO_EXPOSE = fme_feature_type
    ATTR_ACCUM_MODE = Merge Initiator and Result
    ATTR_CONFLICT_RES = Use Result
    COMBINE_GEOM = Use Result
    DATASET = @Value(_lastools_temp_output)
    FEATURETYPES_RADIO = FEATURETYPES
    FORMAT = LAS
    INTERACT = <No Spatial Filter>
    LAS_CLIP_TO_ENVELOPE = NO
    LAS_GROUP_BY_DATASET = Yes
    LAS_USE_SEARCH_ENVELOPE = NO
    OUTPUT_FEATURES_DISPLAY = Based on Connections
    <OTHER> -> TestFilter_3
TestFilter_3
    DEFAULT_VALUE = Use lastools output
    TEST_LIST = BOOL_OP,OR,COMPOSITE_TEST,<Unused>,TEST_CLAUSE,"TEST $(LASMERGE) = Merge with the source",Merge with the source
    Merge with the source -> PointCloudComponentKeeper
    Use lastools output -> FMEFunctionCaller_2
Note: Keep only added (modified) component
PointCloudComponentKeeper
    COMPONENTS_TO_KEEP = x,y,z,classification
    -> PointCloudMerger [SUPPLIER]
Note: Merge original point clouds with modified by XYZ. / Not very important for LAS files, / but may be very important for other point clouds / - this way we preserve their original components
PointCloudMerger
    COMPONENTS_TO_JOIN = x x y y z z
    GROUP_BY = _lastools_temp_output
    HANDLE_CONFLICT = Use Supplier
    MERGED -> FMEFunctionCaller_2
Note: Issue a command for the output point cloud to kill itself / once it is not needed
FMEFunctionCaller_2
    FUNC = @Geometry(DELETE_SOURCE_DATASET)
    -> SystemCaller_3
Note: Some files won't be deleted by @geometry function / Delete temp files. Each feature deletes its own files. / Adjust TCL path name to Windows by replacing / forward slash with backslash / del @ReplaceString(@Value(_lastools_temp_input),/,\) /Q
SystemCaller_3
    ATTR = _exit_code
    CMD = del "@ReplaceString(@Value(_lastools_temp_input),/,\)" /Q
    -> AttributeRemover_3
Note: Remove temp attributes / Keep temp_output for joining the original fme_basename
AttributeRemover_3
    REMOVE_ATTRS = _dirpath,_modified,fme_basename,_rootname,_filename,_lastools_count,_total_features_written,_dirname,_dataset,_element_index,las_type,_lastools_command_line,_lastools_name,_lastools_temp_input,_source_format,fme_feature_type,_exit_code,_extension
    -> FeatureMerger_2 [REQUESTOR]
Note: Merge to pass fme_basename to the output
FeatureMerger_2
    ATTR_ACCUM_MODE = Merge Supplier
    ATTR_CONFLICT_RES = Use Requestor
    IGNORE_NULLS = No
    JOIN_KEYS = @Value(_lastools_temp_output) @Value(_lastools_temp_output) AUTO
    MERGE_TYPE = Attributes Only
    PROCESS_DUPS = No
    SUPPLIERS_FIRST = No
    MERGED -> AttributeExposer_3
AttributeExposer_3
    ATTR_LIST = fme_feature_type,_source_dataset
    -> AttributeRemover_2
Note: Remove attributes
AttributeRemover_2
    REMOVE_ATTRS = _source_format,_modified,_source_dataset,_lastools_temp_input,_lastools_temp_output,_rootname,las_type,_dirpath,_extension,fme_feature_type,_filename,_dirname
    -> GroundClassified (output)
GroundClassified (output)
Terminator
    MESSAGE = Translation Terminated. lasground.exe wasn't executed successfully

Bookmark: Reserve names for intermediate files
Note: Reserve a name for temp input for LAStools
TclCaller_2
    TCLPROG = FME_TempFilename input .las
    VAL_ATTR = _lastools_temp_input
    -> TclCaller_3
Note: Reserve a name for temp output for LAStools
TclCaller_3
    TCLPROG = FME_TempFilename output .las
    VAL_ATTR = _lastools_temp_output
    -> FilenamePartExtractor

FME custom transformer SurfaceNormalExtractor
Calculates surface normal vectors on Faces from the average of the existing surface vertex normals. If no vertex normals exist, they will be generated by a GeometryValidator.
Normals will be stored as the following traits on each Face:
surface_normal_x
surface_normal_y
surface_normal_z
The SurfaceNormalExtractor will work on Composite and MultiSurfaces as well, with no need to de-aggregate. Meshes will be automatically converted to Composite Surfaces.
**Input**
Source features
**Output**
Output features with calculated surface normals

Input (input)
    -> GeometryCoercer_2
Note: Convert other surface types / to faced based surface
GeometryCoercer_2
    GQUERY:
      for $geom in //geometry
      where $geom/@fme_geometry_type = 'IFMEMesh'
      or $geom/@fme_geometry_type = 'IFMERectangleFace'
      or $geom/@fme_geometry_type = 'IFMETriangleFan'
      or $geom/@fme_geometry_type = 'IFMETriangleStrip'
      return number($geom/@fme_id)
    KIND = fme_composite_surface
    COERCED -> GeometryValidator
    UNTOUCHED -> GeometryValidator
Note: Generate vertex / normals if needed
GeometryValidator
    ISSUE_ATTR_NAME = _surface_normal_issues
    MISSING_VERTEX_NORMALS = MISSING_VERTEX_NORMALS
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = None
    PASSED -> GeometryPropertySetter
    REPAIRED -> GeometryPropertySetter
Note: Create Face ids
GeometryPropertySetter
    CNT_ATTR = _surface_normal_id
    DOMAIN = _surface_normal_id
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor
    SET -> GeometryPropertySetter_UNTOUCHED_-__TraitMerger_REQUESTOR
    UNTOUCHED -> GeometryPropertySetter_UNTOUCHED_-__TraitMerger_REQUESTOR
    <REJECTED> -> Junction
GeometryPropertySetter_UNTOUCHED_-__TraitMerger_REQUESTOR: Junction
    -> TraitMerger [REQUESTOR]
Note: Extract Faces
GeometryPartExtractor
    EXTRACTTYPE_PARAM = Extract
    GQUERY:
      for $geom in //geometry
      where $geom/@fme_geometry_type = 'IFMEFace'
      return number($geom/@fme_id)
    PROCESSED -> GeometryPropertyExtractor
Note: Extract Face ids
GeometryPropertyExtractor
    EXTRACTTYPE_PARAM = Traits
    PREFIX_EXTRACTED_TRAITS = No
    TRAIT_ATTR_LIST = _surface_normal_id,No
    EXTRACTED -> GeometryCoercer
    UNTOUCHED -> Junction_2
Note: Coerce to polygon / for measure extraction
GeometryCoercer
    GQUERY:
      for $geom in //geometry
      where $geom/count(parent::geometry) = 0
      return number($geom/@fme_id)
    KIND = fme_polygon
    COERCED -> MeasureExtractor
Note: Extract normal measures
MeasureExtractor
    GEOM_TYPE = Whole Area
    MEASURE_LIST = fme_vertex_normal_x
    MEASURE_NAME = fme_vertex_normal_x
    -> MeasureExtractor_2
    <REJECTED> -> Junction_3
MeasureExtractor_2
    GEOM_TYPE = Whole Area
    MEASURE_LIST = fme_vertex_normal_y
    MEASURE_NAME = fme_vertex_normal_y
    -> MeasureExtractor_3
    <REJECTED> -> Junction_3
MeasureExtractor_3
    GEOM_TYPE = Whole Area
    MEASURE_LIST = fme_vertex_normal_z
    MEASURE_NAME = fme_vertex_normal_z
    -> ListSummer
    <REJECTED> -> Junction_3
Note: Sum normal measures
ListSummer
    RESULT = _normal_sum_x
    SRC_LIST = fme_vertex_normal_x{}
    -> ListSummer_2
ListSummer_2
    RESULT = _normal_sum_y
    SRC_LIST = fme_vertex_normal_y{}
    -> ListSummer_3
ListSummer_3
    RESULT = _normal_sum_z
    SRC_LIST = fme_vertex_normal_z{}
    -> ListElementCounter
Note: Count normal measures
ListElementCounter
    CNT_ATTR = _normal_count_x
    LIST_NAME = fme_vertex_normal_x{}
    -> ListElementCounter_2
ListElementCounter_2
    CNT_ATTR = _normal_count_y
    LIST_NAME = fme_vertex_normal_y{}
    -> ListElementCounter_3
ListElementCounter_3
    CNT_ATTR = _normal_count_z
    LIST_NAME = fme_vertex_normal_z{}
    -> AttributeCreator
Note: Calculate surface normal / from average of vertex / normals
AttributeCreator
    ATTR_TABLE:
      SET_TO surface_normal_x = @Evaluate(@Value(_normal_sum_x)/@Value(_normal_count_x))
      SET_TO surface_normal_y = @Evaluate(@Value(_normal_sum_y)/@Value(_normal_count_y))
      SET_TO surface_normal_z = @Evaluate(@Value(_normal_sum_z)/@Value(_normal_count_z))
    -> GeometryPropertySetter_2
Note: Set surface normal as traits
GeometryPropertySetter_2
    OVERWRITE_CHOICE = Yes
    REMOVE_ATTRIBUTE = No
    SETTYPE_PARAM = Traits From Attributes
    SRC_ATTRS = surface_normal_x _surface_normal_id surface_normal_z surface_normal_y
    SET -> AttributeRemover
    <REJECTED> -> Junction_4
Note: Remove uneeded attributes
AttributeRemover
    LIST_ATTRS = _surface_normal_issues{} fme_vertex_normal_x{} fme_vertex_normal_y{} fme_vertex_normal_z{}
    REMOVE_ATTRS = _normal_sum_x,surface_normal_x,_normal_sum_y,_normal_count_x,_normal_sum_z,_surface_normal_id,surface_normal_z,surface_normal_y
    -> AttributeKeeper_2
AttributeKeeper_2
    CREATE_BULK_MODE_FEATURES = No
    -> TraitMerger [SUPPLIER]
Note: Merge normal traits on / Faces by Face id
TraitMerger
    ATTR_ACCUM_MODE = Merge Supplier
    ATTR_CONFLICT_RES = Use Requestor
    COMPONENTS_TO_JOIN = _surface_normal_id;_surface_normal_id
    REQUESTOR_TYPE = Trait
    R_GQUERY:
      for $geom in //geometry
      where $geom/@fme_geometry_type = 'IFMEFace'
      return number($geom/@fme_id)
    SUPPLIER_TYPE = Trait
    S_GQUERY:
      for $geom in //geometry
      where $geom/count(parent::geometry) = 0
      return number($geom/@fme_id)
    RESULT -> GeometryPropertyRemover
    UNTOUCHED -> GeometryPropertyRemover
Note: Remove Face id
GeometryPropertyRemover
    REGEX_FILTER = _surface_normal_id
    REMOVETYPE_PARAM = Traits
    REMOVE_ALL = No
    REMOVED -> AttributeRemover_2
    UNTOUCHED -> AttributeRemover_2
Note: Remove uneeded attributes
AttributeRemover_2
    LIST_ATTRS = _surface_normal_issues{}
    -> Output (output)
Output (output)
Junction
    -> Junction_2
Junction_2
    -> Junction_3
Junction_3
    -> Junction_4
Junction_4
